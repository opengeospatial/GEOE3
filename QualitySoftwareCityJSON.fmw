FME workspace QualitySoftwareCityJSON.fmw

Parameters:
- INPUT_CITYJSON = C:\Users\ATURUNEN\Downloads\building_ES.json   # Source CityJSON File(s)
- OUTPUT_CSV = $(FME_MF_DIR)results_ES   # Output CSV File containing errors
- OUTPUT_CITYJSON = $(FME_MF_DIR)results_ES.json   # Destination CityJSON File
- OUTPUT_CRS =   # EnableReadFromFeature:No Destination Coordinate System (emtpy: use original)
- RULE_CATEGORIES = ValidateGeometry   # Rule categories to be checked
- Transformer_parameters = FME_DISCLOSURE_OPEN   # Threshold parameters (if empty, skip the rule)
- CHECK_NORMALS = Yes   # Check vertex normals
- OVERLAP = 0   # Maximum overlapping percentage of the whole area (0-100 %)
- PLAN_DIST = 0.01   # Planar surface tolerance based on distance ie. 'thickness'
- PLAN_ANG = 20   # Planar surface tolerance based on normal deviation (degrees)
- MIN_VOLUME = 1   # Minimum volume of the solid objects
- MIN_AREA = 1   # Minimum area of the surface
- SPIKEANGLE = 10   # Maximum Spike Angle (degrees)
- COORD_PREC =   # Coordinate rounding precision (desimals)
- TOLERANCE = 0.001   # Tolerance for duplicative concecutive points

Readers:
- CITYJSON_1: CITYJSON from $(INPUT_CITYJSON)

Writers:
- CITYJSON_2: CITYJSON to $(OUTPUT_CITYJSON)
- CSV2_1: CSV2 to C:\Users\ATURUNEN\Work Folders\FME+DB

Note: Note: Only CityJSON v1.0.1 is supported :(
Junction
    -> Tester_2
Tester_2
    BOOL_OP = OR
    TEST_CLAUSE = CASE_INSENSITIVE_TEST $(RULE_CATEGORIES) CONTAINS ValidateGeometry
    TEST_MODE = CASE_INSENSITIVE_TEST
    PASSED -> ValidateGeometry [GeometryValidatorInput]
ValidateGeometry
    CHECK_NORMALS = $(CHECK_NORMALS)
    FID = @Value(fid)
    FME_DATASET = @Value(fme_dataset)
    FME_FEATURE_TYPE = @Value(fme_feature_type)
    FME_GEOMETRY = @Value(fme_geometry)
    FME_TYPE = @Value(fme_type)
    MIN_AREA = $(MIN_AREA)
    MIN_VOLUME = $(MIN_VOLUME)
    OVERLAP = $(OVERLAP)
    PLAN_ANG = $(PLAN_ANG)
    PLAN_DIST = $(PLAN_DIST)
    SPIKEANGLE = $(SPIKEANGLE)
    TOLERANCE = $(TOLERANCE)
    TabularErrors -> AttributeKeeper_2
    ErrorsWithGeometry -> Tester
Note: Check rule categories
Tester_5
    BOOL_OP = OR
    TEST_CLAUSE = CASE_INSENSITIVE_TEST $(RULE_CATEGORIES) CONTAINS ValidateAttributes
    TEST_MODE = TEST
    PASSED -> ValidateAttributes
ValidateAttributes
    FID = @Value(fid)
    FME_DATASET = @Value(fme_dataset)
    FME_FEATURE_TYPE = @Value(fme_feature_type)
    FME_GEOMETRY = @Value(fme_geometry)
    ROOFTYPE = @Value(roofType)
    AllAttributeErrors -> AttributeKeeper_2

Bookmark: Inpu CityJSON data from folder
Building (reader CITYJSON_1)
    attributes: fid string, AbsoluteEavesHeight real64, AbsoluteRidgeHeight real64, RelativeEavesHeight real64, RelativeRidgeHeight real64, roofType string
    -> DuplicateIDFilter
BuildingPart (reader CITYJSON_1)
    attributes: fid string, AbsoluteEavesHeight real64, AbsoluteRidgeHeight real64, RelativeEavesHeight real64, RelativeRidgeHeight real64, roofType string
    -> DuplicateIDFilter

Bookmark: Find duplicates and prepare data
Note: Check duplicate fids
DuplicateIDFilter: DuplicateFilter
    INPUT_ORDERED_CHOICE = No
    KEYATTR = fid
    UNIQUE -> AppearanceRemover
    DUPLICATE -> AttributeCreator_3
AppearanceRemover
    SIDE_TO_REMOVE = Front and Back Sides
    -> Junction_2
    <REJECTED> -> Junction_2
Junction_2
    -> GeometryFilter
    -> Tester_5
Note: Check null geometries
GeometryFilter
    BREAK_AGG = No
    GEOM_PORT_NAMES = Null
    NULL -> AttributeCreator_5
    <UNFILTERED> -> AttributeKeeper
AttributeCreator_5
    ATTR_TABLE:
      SET_TO error_name = MissingGeometry
      SET_TO details = The feature does not have geometry.
      SET_TO severity_level = FAIL
      SET_TO count = 1
    -> AttributeKeeper_2
Note: Keep only relevant attibutes
AttributeKeeper
    CREATE_BULK_MODE_FEATURES = NO
    KEEP_ATTRS = fid,fme_dataset,fme_feature_type,fme_geometry,fme_type
    KEEP_LIST = cityjson_children{} cityjson_parents{}
    -> FindDuplicateGeometries
Note: Check duplicate geometries
FindDuplicateGeometries: Matcher
    CHECK_COORDINATE_SYSTEMS = No
    LENIENT_MATCH = Yes
    MATCH = 3D
    MATCHED -> AttributeCreator_2
    SINGLE_MATCHED -> CheckCRS
    NOT_MATCHED -> CheckCRS
AttributeCreator_2
    ATTR_TABLE:
      SET_TO error_name = DuplicateGeometry
      SET_TO details = Geometry of the feature is not unique
      SET_TO severity_level = FAIL
      SET_TO count = 1
    -> AttributeKeeper_2
    -> Tester
CheckCRS
    COORD_PREC = $(COORD_PREC)
    DEST_CRS = $(OUTPUT_CRS)
    FID = @Value(fid)
    FME_DATASET = @Value(fme_dataset)
    FME_FEATURE_TYPE = @Value(fme_feature_type)
    FME_GEOMETRY = @Value(fme_geometry)
    FME_TYPE = @Value(fme_type)
    Passed -> Junction
    TabularErrors -> AttributeKeeper_2
    ErrorsWithGeometry -> Tester
AttributeCreator_3
    ATTR_TABLE:
      SET_TO error_name = DuplicateID
      SET_TO details = The FID is not unique among all features in the dataset.
      SET_TO severity_level = FAIL
      SET_TO count = 1
    -> AttributeKeeper_2

Bookmark: Write features with *geometry* errors to CityJSON
Note: See, if DEST_CITYJSON is determined in the user parameters. If yes, write results to CityJSON.
Tester
    BOOL_OP = OR
    TEST_CLAUSE = TEST $(OUTPUT_CITYJSON) != ""
    TEST_MODE = TEST
    PASSED -> FilenamePartExtractor_2
FilenamePartExtractor_2
    EXTENSION_ATTR = _extension
    FULLNAME_ATTR = _filename
    SRC_ATTR = $(OUTPUT_CITYJSON)
    -> AttributeRenamer_3
AttributeRenamer_3
    ATTR_TABLE = RENAME_SET_DEFAULT fid > orig_fid
    MISSING_INPUT_ATTRS = REMOVE
    -> Counter
Counter
    CNT_ATTR = fid
    GROUP_BY = fme_dataset
    SCOPE = Local
    START = 0
    -> FeatureTypeFilter
FeatureTypeFilter
    ATTRIBUTES = <Blank>,<Unfiltered>,Building,BuildingPart,BuildingInstallation
    Building -> Building (writer CITYJSON_2)
    BuildingPart -> BuildingPart (writer CITYJSON_2)
    BuildingInstallation -> BuildingInstallation (writer CITYJSON_2)
Building (writer CITYJSON_2)
    attributes: error_name string, severity_level string, fid string, details string
BuildingPart (writer CITYJSON_2)
    attributes: error_name string, severity_level string, fid string, details string
BuildingInstallation (writer CITYJSON_2)
    attributes: error_name string, severity_level string, fid string, details string

Bookmark: Group and clean errors. Save all errors per the dataset to TSV file.
AttributeKeeper_2
    CREATE_BULK_MODE_FEATURES = NO
    KEEP_ATTRS = error_name,fme_dataset,fme_feature_type,severity_level,details,fme_type,count,fid
    -> NullAttributeMapper
NullAttributeMapper
    ATTRCHOICE = Selected Attributes
    ATTRLIST = count
    NEW_VALUE = 1
    NULL_TREATMENT = New Value
    SOURCE_ATTR_VAL = Null Empty "Missing (Selected Attributes Only)"
    -> GeometryRemover
GeometryRemover
    -> ErrorsPerFeature
    -> ErrorsPerDataset
Note: All errors and their counts per dataset
ErrorsPerDataset: StatisticsCalculator
    CALCULATION_MODE = NUMERIC
    FEAT_STATS = count,NUMERIC_MODE,,,,SUM,,,,,,,,,
    GROUP_BY = error_name fme_dataset details severity_level
    SUMMARY -> AttributeRenamer_2
AttributeRenamer_2
    ATTR_TABLE = RENAME_SET_DEFAULT count.sum > error_count
    MISSING_INPUT_ATTRS = REMOVE
    -> Inspector
    -> Tester_6
Note: See, if OUTPUT_CSV is determined in the user parameters. If yes, write results to tsv.
Tester_6
    BOOL_OP = OR
    TEST_CLAUSE = TEST $(OUTPUT_CSV) != ""
    TEST_MODE = TEST
    PASSED -> StringReplacer
StringReplacer
    CASE = NO
    FIND_TEXT = ,
    NO_MATCH = _FME_NO_OP_
    REGEXP = NO
    SRC_ATTRS = details
    -> FilenamePartExtractor
FilenamePartExtractor
    DIRNAME_ATTR = _dirname
    DIRPATH_ATTR = _dirpath
    EXTENSION_ATTR = _extension
    FULLNAME_ATTR = _filename
    ROOTNAME_ATTR = _rootname
    SRC_ATTR = $(OUTPUT_CSV)
    -> File1 (writer CSV2_1)
File1 (writer CSV2_1)
    attributes: details string, error_name string, error_count string, severity_level string, dataset string
Note: Click to see resuls:
Inspector
ErrorsPerFeature: StatisticsCalculator
    CALCULATION_MODE = NUMERIC
    FEAT_STATS = count,NUMERIC_MODE,,,,SUM,,,,,,,,,
    GROUP_BY = fid error_name details severity_level fme_dataset
    SUMMARY -> Aggregator
Note: All aggregated errors per feature. One feature might contain multiple errors.
Aggregator
    ACCUM_ATTRS_NAME = Drop Incoming Attributes
    CONCAT_ATTRS = details error_name severity_level
    GROUP_BY = fid
    MODE = Attributes Only
    SEP = " & "
    SUM = count.sum
    AGGREGATE -> Inspector_3
Note: Click to see resuls:
Inspector_3

FME custom transformer CheckCRS

Parameters:
- Transformer_parameters = FME_DISCLOSURE_OPEN   # COORD_PREC Threshold parameters
- COORD_PREC = 3   # Coordinate rounding precision (desimals)
- DEST_CRS =   # EnableReadFromFeature:No Destination Coordinate System (emtpy: use original)
- FME_DATASET = @Value(fme_dataset)   # Fme Dataset
- FID = @Value(fid)   # fid
- FME_FEATURE_TYPE = @Value(fme_feature_type)   # Fme Feature Type
- FME_GEOMETRY = @Value(fme_geometry)   # Fme Geometry
- FME_TYPE = @Value(fme_type)   # Fme Type

Input (input)
    -> CoordinateSystemExtractor
CoordinateSystemExtractor
    CRDSYS_ATTR = _coordsys
    -> DimensionExtractor
DimensionExtractor
    DIM_ATTR = _dimension
    -> CheckCRS
Note: Check CRS existence
CheckCRS: Tester
    BOOL_OP = OR
    TEST_CLAUSE = TEST _coordsys ATTRIBUTE_HAS_A_VALUE ""
    TEST_MODE = TEST
    PASSED -> Check3D
    FAILED -> AttributeCreator
Note: Check 3D
Check3D: Tester
    BOOL_OP = OR
    TEST_CLAUSE = TEST @Value(_dimension) = 3
    TEST_MODE = TEST
    PASSED -> GeometryValidator
    FAILED -> AttributeCreator_4
Note: Check mismatcher dimensions
GeometryValidator
    ISSUE_ATTR_NAME = _issues
    PRESETS = Custom
    REPAIR = No
    RULES = MISMATCHED_DIMENSIONS FORCE_DIMENSION]3D]MISMATCHED_Z_VAL]0]FME_CONTROLLER_QUERY_FILE]transformers/dependencies/geometryvalidator8/MISMATCHED_DIMENSIONS.fme]FME_CONTROLLER_CHOICE]MISMATCHED_DIMENSIONS
    SUMMARY = Brief
    PASSED -> AttributeRemover
    ISSUE_LOCATIONS -> AttributeCreator_3
    INVALID_PARTS -> ListExploder_2
AttributeRemover
    REMOVE_ATTRS = _coordsys,_dimension
    -> Tester_7
Note: See if DEST_CRS is defined in user parameters.
Tester_7
    BOOL_OP = OR
    TEST_CLAUSE = TEST $(DEST_CRS) != ""
    TEST_MODE = TEST
    PASSED -> CsmapReprojector
    FAILED -> Tester_2
Note: If yes, reproject the data.
CsmapReprojector
    DEST = $(DEST_CRS)
    INTERPOLATION_TYPE_NAME = Nearest Neighbor
    RASTER_CELL_SIZE = Preserve Cells
    RASTER_TOLERANCE = 0.0
    VERTICAL_HANDLING = Heights are relative to the ellipsoid(s) or geocentric
    REPROJECTED -> Tester_2
Note: See if COORD_PREC has a value in user parameters.
Tester_2
    BOOL_OP = OR
    TEST_CLAUSE = TEST $(COORD_PREC) != ""
    TEST_MODE = TEST
    PASSED -> CoordinateRounder
    FAILED -> Passed (output)
Note: If yes, round coordinates
CoordinateRounder
    XPREC = $(COORD_PREC)
    YPREC = $(COORD_PREC)
    ZPREC = $(COORD_PREC)
    ROUNDED -> Passed (output)
Passed (output)
AttributeCreator_3
    ATTR_TABLE:
      SET_TO error_name = _issues
      SET_TO severity_level = FAIL
    -> GeometryRemover
Note: Expose the list of errors including error name
ListExploder_2
    ATTR_ACCUM_MODE = Merge List Attributes
    ATTR_CONFLICT_RES = Use List Attribute Values
    LIST_ATTR = _issues{}
    ELEMENTS -> ListExploder_4
Note: Expose details
ListExploder_4
    ATTR_ACCUM_MODE = Merge List Attributes
    ATTR_CONFLICT_RES = Use List Attribute Values
    LIST_ATTR = supplementary_info{}
    ELEMENTS -> AttributeManager_2
Note: Remove and format attributes
AttributeManager_2
    ATTR_TABLE:
      RENAME_SET_DEFAULT count = 1
      RENAME_SET_VALUE issue_found > error_name
      REMOVE location_sample.x
      REMOVE location_sample.y
      REMOVE location_sample.z
      RENAME_SET_DEFAULT supplementary_info > details = FME_CONDITIONAL:DEFAULT_VALUE'_FME_NO_OP_'BOOL_OP;OR;COMPOSITE_TEST;1;TEST details ATTRIBUTE_IS_MISSING _FME_BLANK_STRING_'Miscellanous'FME_NUM_CONDITIONS2___
      REMOVE _coordsys
      REMOVE _dimension
      SET_TO severity_level = FAIL
    -> ErrorsWithGeometry (output)
ErrorsWithGeometry (output)
AttributeCreator_4
    ATTR_TABLE:
      SET_TO error_name = Not3D
      SET_TO details = Coordinate reference system is not 3D
      SET_TO severity_level = FAIL
    -> GeometryRemover
AttributeCreator
    ATTR_TABLE:
      SET_TO error_name = MissingCRS
      SET_TO details = Coordinate reference system does not exist
      SET_TO severity_level = FAIL
    -> GeometryRemover
GeometryRemover
    -> CoordinateSystemRemover
CoordinateSystemRemover
    -> TabularErrors (output)
TabularErrors (output)

FME custom transformer ValidateGeometry
This transformer validates all quality problems related to geometry of the CityGML Building dataset. 
Input: CityGML dataset containing Buildings with coordinate reference system
Output: Table containing all geometry problems of the features

Parameters:
- Transformer_parameters = FME_DISCLOSURE_OPEN   # These parameters affect for transformers and thus pass rate of quality rules
- OVERLAP = 5   # Overlapping threshold as a percentage of the whole area (0-100 %)
- PLAN_DIST = 0.05   # Planar surface tolerance based on distance ie. 'thickness'
- PLAN_ANG = 10   # Planar surface tolerance based on normal deviation (degrees)
- MIN_AREA = 1   # Minimum area of the surface
- CHECK_NORMALS = No   # Choose if program check normals for every vertex
- FME_FEATURE_TYPE = @Value(fme_feature_type)   # Fme Feature Type
- FME_DATASET = @Value(fme_dataset)   # Fme Dataset
- FID = @Value(fid)   # fid
- MIN_VOLUME = 1   # Minimum volume of the solid
- SPIKEANGLE = 10   # Maximum Spike Angle
- FME_GEOMETRY = @Value(fme_geometry)   # Fme Geometry
- FME_TYPE = @Value(fme_type)   # Fme Type
- TOLERANCE = 0   # Tolerance for duplicate concecutive points

Note: Some transformers will modify or discard the data because otherwise the data might not be suitable for the rest of rules. / (Thus do not change the order of bookmarks or transformers without proper reason)
GeometryValidatorInput (input)
    -> RemoveInvalidGeometries
Junction
    -> CheckAllOtherProblems
    -> CheckSelfIntersectionsIn2D
    -> Junction_3
    -> CheckAndFixOGC

Bookmark: Prepare geometry
Note: Fix NaNs, infinities, degenerated and corrupted geometries. Also remove concecutive duplicate points.
RemoveInvalidGeometries: GeometryValidator
    ISSUE_ATTR_NAME = _issues
    PRESETS = Custom
    REPAIR = Yes
    RULES = NAN_REMOVAL PROCESS_MEASURE]NO]FME_CONTROLLER_QUERY_FILE]transformers/dependencies/geometryvalidator/NAN_REMOVAL.fme]FME_CONTROLLER_CHOICE]NAN_REMOVAL TYPE_REPAIR SOURCE]]CONNECT_Z_MODE]FIRST_WINS]ARC_ENDPOINT_TOLERANCE_MODE]Auto]ARC_ENDPOINT_TOLERANCE]0.0]FME_CONTROLLER_QUERY_FILE]transformers/dependencies/geometryvalidator/TYPE_REPAIR.fme]FME_CONTROLLER_CHOICE]TYPE_REPAIR CONSECUTIVE_IDENTICAL_VERTICES_2D CHECK_Z]YES]TOLERANCE]$(TOLERANCE)]FME_CONTROLLER_QUERY_FILE]transformers/dependencies/geometryvalidator/CONSECUTIVE_IDENTICAL_VERTICES_2D.fme]FME_CONTROLLER_CHOICE]CONSECUTIVE_IDENTICAL_VERTICES_2D
    SUMMARY = Detailed
    PASSED -> Junction
    REPAIRED -> Junction
    ISSUE_LOCATIONS -> AttributeCreator_FIXED
    INVALID_PARTS -> ListExploder_3

Bookmark: Embedded transformers
Junction_3
    -> GroundOverlappingIn2D
    -> CheckSpikes
    -> CheckAreaAndVolume
    -> CompareRoofToFloor
    -> CheckNormals
CheckNormals
    CheckVertexNormals = $(CHECK_NORMALS)
    FID = @Value(fid)
    FME_DATASET = @Value(fme_dataset)
    FME_FEATURE_TYPE = @Value(fme_feature_type)
    FME_TYPE = @Value(fme_type)
    Errors -> AttributeCreator_NOTE
    IssueLocations -> ListExploder_3
GroundOverlappingIn2D
    FID = @Value(fid)
    FME_DATASET = @Value(fme_dataset)
    FME_FEATURE_TYPE = @Value(fme_feature_type)
    OVERLAP = $(OVERLAP)
    IssueLocations -> ListExploder_3
    Errors -> AttributeCreator_NOTE
CompareRoofToFloor
    FID = @Value(fid)
    FME_DATASET = @Value(fme_dataset)
    FME_FEATURE_TYPE = @Value(fme_feature_type)
    Errors -> AttributeCreator_NOTE
CheckAreaAndVolume
    FID = @Value(fid)
    FME_DATASET = @Value(fme_dataset)
    FME_FEATURE_TYPE = @Value(fme_feature_type)
    FME_GEOMETRY = @Value(fme_geometry)
    FME_TYPE = @Value(fme_type)
    MIN_AREA = $(MIN_AREA)
    MIN_VOLUME = $(MIN_VOLUME)
    Errors -> AttributeCreator_NOTE
    IssueLocations -> ListExploder_3
CheckSpikes
    FID = @Value(fid)
    FME_DATASET = @Value(fme_dataset)
    FME_FEATURE_TYPE = @Value(fme_feature_type)
    FME_GEOMETRY = @Value(fme_geometry)
    SPIKEANGLE = $(SPIKEANGLE)
    Errors -> AttributeCreator_NOTE
    IssueLocations -> ListExploder_3

Bookmark: Check all other problems
CheckAndFixOGC: GeometryValidator
    ISSUE_ATTR_NAME = _issues
    PRESETS = Custom
    REPAIR = Yes
    RULES = OGC_VALID_CHECK OGC_VERSION]V1.2.0]LEGACY_OGC]No]FME_CONTROLLER_QUERY_FILE]transformers/dependencies/geometryvalidator8/OGC_VALID_CHECK.fme]FME_CONTROLLER_CHOICE]OGC_VALID_CHECK OGC_SIMPLE_CHECK FME_CONTROLLER_QUERY_FILE]transformers/dependencies/geometryvalidator8/OGC_SIMPLE_CHECK.fme]FME_CONTROLLER_CHOICE]OGC_SIMPLE_CHECK]LEGACY_OGC]No
    SUMMARY = Detailed
    FAILED -> ListExploder_6
    INVALID_PARTS -> ListExploder_3
Note: Explode features because OGC rules do not provide issue locations
ListExploder_6
    ATTR_ACCUM_MODE = Merge List Attributes
    ATTR_CONFLICT_RES = Use List Attribute Values
    LIST_ATTR = _issues{}
    ELEMENTS -> AttributeFilter_3
AttributeFilter_3
    ATTR_NAME = issue_found
    ATTR_VALUES = <Empty>,<Missing>,<Null>,<Unfiltered>,Fails OGC Simple
    <UNFILTERED> -> AttributeCreator_FIXED
    Fails OGC Simple -> AttributeCreator_NOTE
CheckAllOtherProblems: GeometryValidator
    ISSUE_ATTR_NAME = _issues
    PRESETS = Custom
    REPAIR = No
    RULES = AREA_ORIENTATION AREA_ORIENTATION]VALID]FME_CONTROLLER_QUERY_FILE]transformers/dependencies/geometryvalidator8/AREA_ORIENTATION.fme]FME_CONTROLLER_CHOICE]AREA_ORIENTATION MISSING_MEASURES_AND_ELEVATIONS MISSING_VALUES_MODE]SENTINEL]MISSING_MEASURES_MODE]<Unused>]SENTINEL_VALUE]0]LENGTH_DIMENSION]<Unused>]FME_CONTROLLER_QUERY_FILE]transformers/dependencies/geometryvalidator8/MISSING_MEASURES_AND_ELEVATIONS.fme]FME_CONTROLLER_CHOICE]MISSING_MEASURES_AND_ELEVATIONS SURFACE_ORIENTATION FME_CONTROLLER_QUERY_FILE]transformers/dependencies/geometryvalidator8/SURFACE_ORIENTATION.fme]FME_CONTROLLER_CHOICE]SURFACE_ORIENTATION SOLID_ORIENTATION FME_CONTROLLER_QUERY_FILE]transformers/dependencies/geometryvalidator8/SOLID_ORIENTATION.fme]FME_CONTROLLER_CHOICE]SOLID_ORIENTATION PLANAR_SURFACE CHECK_AREA]DO_CHECK_AREA]TOLERANCE_MODE]CUSTOM]TOLERANCE]$(PLAN_DIST)]ANGULAR_TOLERANCE_MODE]CUSTOM]ANGULAR_TOLERANCE]$(PLAN_ANG)]FME_CONTROLLER_QUERY_FILE]transformers/dependencies/geometryvalidator8/PLANAR_SURFACE.fme]FME_CONTROLLER_CHOICE]PLANAR_SURFACE
    SUMMARY = Detailed
    ISSUE_LOCATIONS -> AttributeCreator_NOTE
    INVALID_PARTS -> ListExploder_3

Bookmark: Check self-intersections and repair solid boundaries. After that check solid voids
CheckSelfIntersectionsIn2D: GeometryValidator
    ISSUE_ATTR_NAME = _issues
    PRESETS = Custom
    REPAIR = No
    RULES = SELF_INTERSECTING CHECK_HOLE_TOUCHING_POLYGON]No]CONNECT_Z_MODE_SI]FIRST_WINS]SELF_INTERSECTION_TOLERANCE]None]INTERSECT_ACROSS_MULTIS]Yes]FME_CONTROLLER_QUERY_FILE]transformers/dependencies/geometryvalidator8/SELF_INTERSECTING.fme]FME_CONTROLLER_CHOICE]SELF_INTERSECTING
    SUMMARY = Detailed
    PASSED -> CheckAndFixSolid
    ISSUE_LOCATIONS -> AttributeCreator_FAIL
    INVALID_PARTS -> ListExploder_3
CheckAndFixSolid: GeometryValidator
    ISSUE_ATTR_NAME = _issues
    PRESETS = Custom
    REPAIR = Yes
    RULES = SHELL_VALIDATION FLIP_APPEARANCE_MODE]FLIP_APPEARANCES]FME_CONTROLLER_QUERY_FILE]transformers/dependencies/geometryvalidator8/SHELL_VALIDATION.fme]FME_CONTROLLER_CHOICE]SHELL_VALIDATION SOLID_VOID_REPAIR FME_CONTROLLER_QUERY_FILE]transformers/dependencies/geometryvalidator8/SOLID_VOID_REPAIR.fme]FME_CONTROLLER_CHOICE]SOLID_VOID_REPAIR
    SUMMARY = Detailed
    ISSUE_LOCATIONS -> AttributeFilter
    INVALID_PARTS -> ListExploder_3
AttributeFilter
    ATTR_NAME = issue_found
    ATTR_VALUES = <Empty>,<Missing>,<Null>,<Unfiltered>,Invalid Solid Boundaries
    <UNFILTERED> -> AttributeCreator_NOTE
    Invalid Solid Boundaries -> AttributeCreator_FIXED

Bookmark: Add severity levels and create output
AttributeCreator_FAIL
    ATTR_TABLE = SET_TO severity_level = FAIL
    -> Junction_2
AttributeCreator_NOTE
    ATTR_TABLE = SET_TO severity_level = NOTE
    -> Junction_2
AttributeCreator_FIXED
    ATTR_TABLE = SET_TO severity_level = FIXED
    -> Junction_2
Junction_2
    -> GeometryRemover
GeometryRemover
    -> CoordinateSystemRemover
CoordinateSystemRemover
    -> AttributeManager_2
AttributeManager_2
    ATTR_TABLE:
      SET_TO count = FME_CONDITIONAL:DEFAULT_VALUE'_FME_NO_OP_'BOOL_OP;OR;COMPOSITE_TEST;1;TEST _issues{0}.count ATTRIBUTE_HAS_A_VALUE _FME_BLANK_STRING_'@Value(_issues{0}.count)'BOOL_OP;OR;COMPOSITE_TEST;1;TEST count NOT_ATTRIBUTE_HAS_A_VALUE _FME_BLANK_STRING_'1'BOOL_OP;OR;COMPOSITE_TEST;1;TEST @Value(count) < 1'1'FME_NUM_CONDITIONS4___
      RENAME_SET_DEFAULT details = Miscellaneous
      RENAME_SET_DEFAULT error_name = @Value(issue_found)
      REMOVE issue_found
    USER_EXPOSED_ATTRIBUTES = supplementary_info{}
    -> Aggregator
Note: Aggregate under single fid
Aggregator
    ACCUM_ATTRS_NAME = Drop Incoming Attributes
    GROUP_BY = details error_name fid fme_dataset fme_feature_type fme_geometry severity_level
    MODE = Attributes Only
    SEP = ,
    SUM = count
    AGGREGATE -> TabularErrors (output)
TabularErrors (output)

Bookmark: Add severity levels and create output containing only geometrical locations of issues
Note: Expose the list of errors
ListExploder_3
    ATTR_ACCUM_MODE = Merge List Attributes
    ATTR_CONFLICT_RES = Use List Attribute Values
    LIST_ATTR = _issues{}
    ELEMENTS -> ListExploder_5
    <REJECTED> -> AttributeManager
Note: Expose details
ListExploder_5
    ATTR_ACCUM_MODE = Merge List Attributes
    ATTR_CONFLICT_RES = Use List Attribute Values
    LIST_ATTR = supplementary_info{}
    ELEMENTS -> AttributeManager
    <REJECTED> -> AttributeManager
Note: Remove and format attributes
AttributeManager
    ATTR_TABLE:
      SET_TO count = FME_CONDITIONAL:DEFAULT_VALUE'_FME_NO_OP_'BOOL_OP;OR;COMPOSITE_TEST;1;TEST count NOT_ATTRIBUTE_HAS_A_VALUE _FME_BLANK_STRING_'1'BOOL_OP;OR;COMPOSITE_TEST;1;TEST @Value(count) < 1'1'FME_NUM_CONDITIONS3___
      RENAME_SET_VALUE issue_found > error_name
      REMOVE location_sample.x
      REMOVE location_sample.y
      REMOVE location_sample.z
      RENAME_SET_DEFAULT supplementary_info > details = FME_CONDITIONAL:DEFAULT_VALUE'_FME_NO_OP_'BOOL_OP;OR;COMPOSITE_TEST;1;TEST details ATTRIBUTE_IS_MISSING _FME_BLANK_STRING_'Miscellanous'FME_NUM_CONDITIONS2___
      REMOVE fme_rejection_code
    -> AttributeFilter_2
AttributeFilter_2
    ATTR_NAME = error_name
    ATTR_VALUES = <Empty>,<Missing>,<Null>,<Unfiltered>,Self-Intersections in 2D,Invalid Solid Boundaries,Degenerate or Corrupt Geometries,Duplicate Consecutive Points in 3D, Contains NaNs or Infinities,Fails OGC Valid
    <UNFILTERED> -> AttributeCreator_NOTE_2
    Self-Intersections in 2D -> AttributeCreator_FAIL_2
    Invalid Solid Boundaries -> AttributeCreator_FIXED_2
    Degenerate or Corrupt Geometries -> AttributeCreator_FIXED_2
    Duplicate Consecutive Points in 3D -> AttributeCreator_FIXED_2
    Contains NaNs or Infinities -> AttributeCreator_FIXED_2
    Fails OGC Valid -> AttributeCreator_FIXED_2
AttributeCreator_NOTE_2
    ATTR_TABLE = SET_TO severity_level = NOTE
    -> ErrorsWithGeometry (output)
AttributeCreator_FAIL_2
    ATTR_TABLE = SET_TO severity_level = FAIL
    -> ErrorsWithGeometry (output)
AttributeCreator_FIXED_2
    ATTR_TABLE = SET_TO severity_level = FIXED
    -> ErrorsWithGeometry (output)
ErrorsWithGeometry (output)

FME custom transformer CheckNormals
Normals check: this embedded transformer checks that every feature has logical orientation depending on its type. For roofs, grounds and walls, x-normals should differ according to following classifications:
Walls: Between -0.1 and 0.1 (almost vertical (0 is exactly vertical))
Roofs: More than 0.1 (not vertical, but face must be up)
Grounds: Exactly -1 (face down)

Parameters:
- FME_DATASET = @Value(fme_dataset)   # Fme Dataset
- FME_TYPE = @Value(fme_type)   # Fme Type
- CheckVertexNormals = No   # Choose if program check normals for every vertex
- FID = @Value(fid)   # fid
- FME_FEATURE_TYPE = @Value(fme_feature_type)   # Fme Feature Type

Input (input)
    -> GeometryPartExtractor
    -> GeometryPartExtractor_2
    -> GeometryPartExtractor_3
Note: Extract surfaces
GeometryPartExtractor
    GQUERY:
      for $geom in //geometry
      where $geom/@fme_geometry_name = 'GroundSurface'
      return number($geom/@fme_id)
    EXTRACTED -> AttributeCreator
Note: This embedded transformer checks that every feature has logical orientation depending on its type. For example, GroundSurfaces must be horizontal and WallSurfaces (almost) vertical.
Note: Add feature type to surfaces
AttributeCreator
    ATTR_TABLE = SET_TO _feature_type = GroundSurface
    -> GeometryValidator_2
GeometryPartExtractor_2
    GQUERY:
      for $geom in //geometry
      where $geom/@fme_geometry_name = 'RoofSurface'
      return number($geom/@fme_id)
    EXTRACTED -> AttributeCreator_3
AttributeCreator_3
    ATTR_TABLE = SET_TO _feature_type = RoofSurface
    -> GeometryValidator_2
GeometryPartExtractor_3
    GQUERY:
      for $geom in //geometry
      where $geom/@fme_geometry_name = 'WallSurface'
      return number($geom/@fme_id)
    EXTRACTED -> AttributeCreator_5
AttributeCreator_5
    ATTR_TABLE = SET_TO _feature_type = WallSurface
    -> GeometryValidator_2
Note: Create vertex normals on faces
GeometryValidator_2
    ISSUE_ATTR_NAME = _issues
    PRESETS = Custom
    REPAIR = Yes
    RULES = MISSING_VERTEX_NORMALS FME_CONTROLLER_QUERY_FILE]transformers/dependencies/geometryvalidator/MISSING_VERTEX_NORMALS.fme]FME_CONTROLLER_CHOICE]MISSING_VERTEX_NORMALS
    SUMMARY = Brief
    PASSED -> MeasureExtractor_2
    REPAIRED -> MeasureExtractor_2
    ISSUE_LOCATIONS -> Tester_2
Note: Extract only z normal of every face
MeasureExtractor_2
    GEOM_TYPE = Individual Vertex by Index
    INDEX = 0
    MEASURE_ATTR = _z_normal
    MEASURE_NAME = fme_vertex_normal_z
    -> TestFilter
Note: Test that every z-normal has correct orientation depending on the feature type. / Faces with negative value of z-normals points downwards and faces with positive values points upwards. When the face is exactly vertical, z-normal is 0.
TestFilter
    DEFAULT_VALUE = Invalid Surfaces
    PASSED_TEST_GROUP_OUTPUT = FIRST
    TEST_LIST:
      "BOOL_OP,AND,COMPOSITE_TEST,""""""1 AND 2"""""",TEST_CLAUSE,TEST @Evaluate(@abs(@Value(_z_normal))) < 0.1
      TEST @Value(_feature_type) = WallSurface",WallSurface OK,"BOOL_OP,AND,COMPOSITE_TEST,""""""1 AND 2"""""",TEST_CLAUSE,TEST @Evaluate(@Value(_z_normal)) = -1
      TEST @Value(_feature_type) = GroundSurface",GroundSurface OK,"BOOL_OP,AND,COMPOSITE_TEST,""""""1 AND 2"""""",TEST_CLAUSE,TEST @Evaluate(@Value(_z_normal)) > 0
      TEST @Value(_feature_type) = RoofSurface",RoofSurface OK
    Invalid Surfaces -> GeometryRemover
    Invalid Surfaces -> AttributeCreator_6
Note: Remove geometry and CRS to format errors
GeometryRemover
    -> CoordinateSystemRemover
CoordinateSystemRemover
    -> Aggregator_2
Note: If orientation is not correct, aggregate faces to single surface feature
Aggregator_2
    ACCUM_ATTRS_NAME = Use Attributes From One Feature
    AGGREGATE_TYPE = Homogeneous Collection (If Possible)
    COUNT_ATTR = count
    GROUP_BY = fid
    MODE = Geometry - Assemble One Level
    SEP = ,
    AGGREGATE -> AttributeCreator_2
Note: Add an error
AttributeCreator_2
    ATTR_TABLE:
      SET_TO error_name = SurfacesWronglyOriented
      SET_TO details = The surfaces of the feature are not correctly oriented based on vertex normals.
    -> Errors (output)
AttributeCreator_6
    ATTR_TABLE:
      SET_TO error_name = SurfacesWronglyOriented
      SET_TO details = The surfaces of the feature are not correctly oriented based on vertex normals.
    -> IssueLocations (output)
Note: See if missing vertex normals would raise an error based on user parameters
Tester_2
    BOOL_OP = OR
    TEST_CLAUSE = TEST $(CheckVertexNormals) = Yes
    TEST_MODE = TEST
    PASSED -> GeometryRemover_2
    PASSED -> AttributeCreator_7
GeometryRemover_2
    -> Aggregator_3
Note: If yes, aggregate faces to single surface feature
Aggregator_3
    ACCUM_ATTRS_NAME = Merge Incoming Attributes
    GROUP_BY = fid details
    MODE = Attributes Only
    SEP = ,
    AGGREGATE -> AttributeCreator_4
Note: Add an error
AttributeCreator_4
    ATTR_TABLE:
      SET_TO error_name = @Value(issue_found)
      SET_TO details = The feature does not contain vertex normals.
    -> Errors (output)
Errors (output)
AttributeCreator_7
    ATTR_TABLE:
      SET_TO error_name = @Value(issue_found)
      SET_TO details = The feature does not contain vertex normals.
    -> IssueLocations (output)
IssueLocations (output)

FME custom transformer GroundOverlappingIn2D
Thia transformer check if two GroundSurfaces are overlapping each other when forced to 2D.

Parameters:
- OVERLAP = 5   # Overlapping threshold as a percentage of the whole area (0-100 %)
- FME_DATASET = @Value(fme_dataset)   # Fme Dataset
- FME_FEATURE_TYPE = @Value(fme_feature_type)   # Fme Feature Type
- FID = @Value(fid)   # fid

Input (input)
    -> Tester
Note: See, if the OVERLAP has a value. If not, skip the rule.
Tester
    BOOL_OP = OR
    TEST_CLAUSE = TEST $(OVERLAP) != ""
    TEST_MODE = TEST
    PASSED -> SurfaceFootprintReplacer
Note: Force to 2D by replacing geometry by its footprint
SurfaceFootprintReplacer
    OFFSET_Z = 0
    SHADOW_MODE = Overhead Shadow
    FOOTPRINT -> GeometryValidator
Note: Fix self-intersection bercause otherwise they would cause unintentional overlap.
GeometryValidator
    ISSUE_ATTR_NAME = _issues
    PRESETS = Custom
    REPAIR = Yes
    RULES = SELF_INTERSECTING CHECK_HOLE_TOUCHING_POLYGON]No]CONNECT_Z_MODE_SI]FIRST_WINS]SELF_INTERSECTION_TOLERANCE]None]INTERSECT_ACROSS_MULTIS]No]FME_CONTROLLER_QUERY_FILE]transformers/dependencies/geometryvalidator8/SELF_INTERSECTING.fme]FME_CONTROLLER_CHOICE]SELF_INTERSECTING
    SUMMARY = None
    PASSED -> AreaCalculator
    REPAIRED -> AreaCalculator
Note: Calculate area for each feature
AreaCalculator
    AREA_ATTR = _original_area
    AREA_TYPE = Plane Area
    MULT = 1
    -> AreaOnAreaOverlayer [AREA]
    -> Aggregator_2
Note: Find overlapping areas. / Add fid of the overlapping parts to the list called overlap
AreaOnAreaOverlayer
    ACCUM_ATTRS_NAME = Use Attributes From One Feature
    CLEANING_TOLERANCE = Automatic
    CONNECT_Z_MODE = First Wins
    DEAGGREGATE_INPUT = Yes
    LIST_ATTRS_TO_INCLUDE = fid
    LIST_NAME = overlaps
    OVC_ATTR = _overlaps
    AREA -> Tester_5
Note: Select only parts which are overlapping
Tester_5
    BOOL_OP = OR
    TEST_CLAUSE = TEST @Value(_overlaps) > 1
    TEST_MODE = TEST
    PASSED -> ExpressionEvaluator_2
Note: Subtract one from _overlaps parameters
ExpressionEvaluator_2
    ACTION = Create New Attribute
    EXPRESSION = @Value(_overlaps)-1
    VAL_ATTR = _overlaps
    -> ListSearcher
Note: Find fid of the one overlapping part.
ListSearcher
    ATTR_VALUE = @Value(fid)
    INDEX_ATTR = _list_index
    LIST_ATTR = overlaps{}.fid
    MATCHTYPE = FIRST_MATCHED_ENCODED
    FOUND -> ListExploder_3
Note: Create a duplicate with another fid to aggregate it to both pieces of features, which are overlapping.
ListExploder_3
    ATTR_ACCUM_MODE = Merge List Attributes
    ATTR_CONFLICT_RES = Use List Attribute Values
    LIST_ATTR = overlaps{}
    ELEMENTS -> Aggregator_2
Note: Aggregate overlapping parts to original footprints
Aggregator_2
    ACCUM_ATTRS_NAME = Merge Incoming Attributes
    AGGREGATE_TYPE = Homogeneous Collection (If Possible)
    GROUP_BY = fid
    MODE = Geometry - Assemble One Level
    SEP = ,
    SUM = _overlaps
    AGGREGATE -> AreaCalculator_3
Note: Calculate an area which contain extra overlapping parts
AreaCalculator_3
    AREA_ATTR = _overlapping_area
    AREA_TYPE = Plane Area
    MULT = 1
    -> ExpressionEvaluator
Note: Calculate overlapping percentage by comparing original area to new area
ExpressionEvaluator
    ACTION = Create New Attribute
    EXPRESSION = (@Value(_overlapping_area)/@Value(_original_area)-1)*100
    VAL_ATTR = _overlap_percentage
    -> TestFilter_2
Note: Compare overlapping percentage to threshold specified in the user parameters.
TestFilter_2
    DEFAULT_VALUE = <UNFILTERED>
    PASSED_TEST_GROUP_OUTPUT = FIRST
    TEST_LIST = "BOOL_OP,OR,COMPOSITE_TEST,""""""1"""""",TEST_CLAUSE,TEST @Value(_overlap_percentage) > $(OVERLAP)",OverlapOverThreshold
    OverlapOverThreshold -> AttributeCreator_2
Note: If overlapping percentage is more than threshold, add an error.
AttributeCreator_2
    ATTR_TABLE:
      SET_TO error_name = GroundOverlappingIn2D
      SET_TO details = The geometry of two or more GroundSurfaces cannot overlap more than $(OVERLAP) % of their areas.
    -> GeometryRemover
    -> IssueLocations (output)
IssueLocations (output)
GeometryRemover
    -> CoordinateSystemRemover
CoordinateSystemRemover
    -> Errors (output)
Errors (output)

FME custom transformer CoordinateSystemMapUnitExtractor
Extracts the map units from the defined coordinate system of the entering features.
Outputs:
_units: This feature's defined map unit.
eg. 'latlong' for degrees, 'm' for meters, 'ft' or 'us-ft' for feet.

Input (input)
    -> CoordinateSystemExtractor
CoordinateSystemExtractor
    CRDSYS_ATTR = _coordsys
    -> CoordinateSystemDescriptionConverter
CoordinateSystemDescriptionConverter
    DIRECTION_LONG = Convert From FME Representation
    KIND_LONG = PROJ.4 String
    SRC = _coordsys
    VAL_ATTR = _proj4_str
    -> StringSearcher_2
StringSearcher_2
    CASE = no
    MATCHED_RESULT_ATTR = _units
    REGEXP = (?<=proj=).*?(?=\s)
    STRING_TO_SEARCH = @Value(_proj4_str)
    MATCHED -> Tester
Tester
    BOOL_OP = OR
    TEST_CLAUSE = TEST @Value(_units) = longlat
    TEST_MODE = TEST
    PASSED -> Output (output)
    FAILED -> StringSearcher
StringSearcher
    CASE = no
    MATCHED_RESULT_ATTR = _units
    REGEXP = (?<=units=).*?(?=\s)
    STRING_TO_SEARCH = @Value(_proj4_str)
    MATCHED -> Output (output)
Output (output)

FME custom transformer CompareRoofToFloor
This transformers compares building heights in a following way:
1. It check that maximum height of the roof is higher than maximum height of the floor 
2. It check that minimum height or the roof is higher than minimum height or the floor
If not, the errors will be listed to output port.

Parameters:
- FME_FEATURE_TYPE = @Value(fme_feature_type)   # Fme Feature Type
- FME_DATASET = @Value(fme_dataset)   # Fme Dataset
- FID = @Value(fid)   # fid

Input (input)
    -> GeometryPartExtractor
    -> GeometryPartExtractor_2
Note: Extract Roof and GroundSurfaces
GeometryPartExtractor
    GQUERY:
      for $geom in //geometry
      where $geom/@fme_geometry_name = 'GroundSurface'
      return number($geom/@fme_id)
    EXTRACTED -> MaxMinGround
Note: Calculate maximum and minimum values for roof and grounds.
MaxMinGround: BoundsExtractor
    ZMAX = _GroundZMax
    ZMIN = _GroundZMin
    -> AggregateToMax_2
    -> AggregateToMin_2
Note: Select only highest and lowest values per building
AggregateToMax_2: StatisticsCalculator
    CALCULATION_MODE = NUMERIC
    FEAT_STATS = _GroundZMax,NUMERIC_MODE,,MAX,,,,,,,,,,,
    GROUP_BY = fme_dataset fme_feature_type fid
    SUMMARY -> FeatureMerger [REQUESTOR]
AggregateToMin_2: StatisticsCalculator
    CALCULATION_MODE = NUMERIC
    FEAT_STATS = _GroundZMin,NUMERIC_MODE,MIN,,,,,,,,,,,,
    GROUP_BY = fme_dataset fme_feature_type fid
    SUMMARY -> FeatureMerger_2 [REQUESTOR]
GeometryPartExtractor_2
    GQUERY:
      for $geom in //geometry
      where $geom/@fme_geometry_name = 'RoofSurface'
      return number($geom/@fme_id)
    EXTRACTED -> MaxMinRoof
MaxMinRoof: BoundsExtractor
    ZMAX = _RoofZMax
    ZMIN = _RoofZMin
    -> AggregateToMax
    -> AggregateToMin
AggregateToMax: StatisticsCalculator
    CALCULATION_MODE = NUMERIC
    FEAT_STATS = _RoofZMax,NUMERIC_MODE,,MAX,,,,,,,,,,,
    GROUP_BY = fme_dataset fme_feature_type fid
    SUMMARY -> FeatureMerger [SUPPLIER]
Note: Merge highest values of the roofs and highest values of the grounds.
FeatureMerger
    ATTR_ACCUM_MODE = Merge Supplier
    ATTR_CONFLICT_RES = Use Requestor
    IGNORE_NULLS = No
    JOIN_KEYS = @Value(fid) @Value(fid) AUTO
    MERGE_TYPE = Attributes Only
    PROCESS_DUPS = NO
    REJECT_NULL_MISSING_KEYS = No
    SUPPLIERS_FIRST = No
    MERGED -> MaxGroundVSMaxRoof
Note: Check that highest value of the roof is higher than highest value of the ground.
MaxGroundVSMaxRoof: Tester
    BOOL_OP = OR
    TEST_CLAUSE = TEST @Value(_RoofZMax.max) >= @Value(_GroundZMax.max)
    TEST_MODE = TEST
    FAILED -> AttributeCreator_2
Note: if not, add an error
AttributeCreator_2
    ATTR_TABLE:
      SET_TO error_name = MaxGroundHigherThanMaxRoof
      SET_TO details = The maximum height of the floor cannot be smaller than maximum height of the roof.
    -> GeometryRemover_2
    -> IssueLocations (output)
AggregateToMin: StatisticsCalculator
    CALCULATION_MODE = NUMERIC
    FEAT_STATS = _RoofZMin,NUMERIC_MODE,MIN,,,,,,,,,,,,
    GROUP_BY = fme_dataset fme_feature_type fid
    SUMMARY -> FeatureMerger_2 [SUPPLIER]
FeatureMerger_2
    ATTR_ACCUM_MODE = Merge Supplier
    ATTR_CONFLICT_RES = Use Requestor
    IGNORE_NULLS = No
    JOIN_KEYS = @Value(fid) @Value(fid) AUTO
    MERGE_TYPE = Attributes Only
    PROCESS_DUPS = NO
    REJECT_NULL_MISSING_KEYS = No
    SUPPLIERS_FIRST = No
    MERGED -> MinGroundVSMinRoof
MinGroundVSMinRoof: Tester
    BOOL_OP = OR
    TEST_CLAUSE = TEST @Value(_GroundZMin.min) <= @Value(_RoofZMin.min)
    TEST_MODE = TEST
    FAILED -> AttributeCreator
AttributeCreator
    ATTR_TABLE:
      SET_TO error_name = MinGroundHigherThanMinRoof
      SET_TO details = The minimum height of the roof cannot be smaller than minimum height of the ground.
    -> GeometryRemover_2
    -> IssueLocations (output)
IssueLocations (output)
Note: Remove geometries to speed up processing
GeometryRemover_2
    -> Errors (output)
Errors (output)

FME custom transformer CheckSpikes

Parameters:
- FID = @Value(fid)   # fid
- FME_DATASET = @Value(fme_dataset)   # Fme Dataset
- FME_FEATURE_TYPE = @Value(fme_feature_type)   # Fme Feature Type
- SPIKEANGLE = 10   # Maximum Spike Angle
- FME_GEOMETRY = @Value(fme_geometry)   # Fme Geometry

Input (input)
    -> Tester
Note: See, if the SPIKE_ANGLE has a value. If not, skip the rule.
Tester
    BOOL_OP = OR
    TEST_CLAUSE = TEST $(SPIKEANGLE) != ""
    TEST_MODE = TEST
    PASSED -> GeometryPartExtractor
Note: Extract surfaces
GeometryPartExtractor
    GQUERY:
      for $geom in //geometry
      where $geom/@fme_geometry_name = 'GroundSurface'
      or $geom/@fme_geometry_name = 'RoofSurface'
      or $geom/@fme_geometry_name = 'WallSurface'
      return number($geom/@fme_id)
    EXTRACTED -> GeometryPartExtractor_2
Note: Drop donuts
GeometryPartExtractor_2
    GQUERY:
      for $geom in //geometry
      where $geom/@fme_geometry_type = 'IFMEDonut'
      return number($geom/@fme_id)
    UNTOUCHED -> GeometryCoercer
Note: Try to convert to polygons
GeometryCoercer
    GQUERY:
      for $geom in //geometry
      where $geom/@fme_geometry_type != 'IFMECompositeSurface'
      and $geom/@fme_geometry_type != 'IFMEMultiSurface'
      return number($geom/@fme_id)
    KIND = fme_polygon
    COERCED -> Aggregator_2
    UNTOUCHED -> Aggregator_2
Note: Aggregate polygonal features into building level, but now in the polygon format
Aggregator_2
    ACCUM_ATTRS_NAME = Use Attributes From One Feature
    AGGREGATE_TYPE = Homogeneous Collection (If Possible)
    GROUP_BY = fid fme_dataset fme_feature_type
    MODE = Geometry - Assemble One Level
    SEP = ,
    AGGREGATE -> SpikeRemover
Note: Detect spikes based on user parameters
SpikeRemover
    DIMENSIONS = 3D
    ITERATIVE = No
    SPIKEANGLE = $(SPIKEANGLE)
    REMOVED -> AttributeCreator_2
    REMOVED -> GeometryRemover
Note: If the feature contain spikes, remove geometry and CRS to format errors
GeometryRemover
    -> CoordinateSystemRemover
CoordinateSystemRemover
    -> Aggregator
Note: Aggregate erros to under single fid
Aggregator
    ACCUM_ATTRS_NAME = Drop Incoming Attributes
    COUNT_ATTR = count
    GROUP_BY = fid fme_dataset fme_feature_type fme_geometry
    MODE = Attributes Only
    SEP = ,
    AGGREGATE -> AttributeCreator_7
Note: Add an error
AttributeCreator_7
    ATTR_TABLE:
      SET_TO error_name = FeatureHasSpikes
      SET_TO details = Feature cannot contain spikes that exceeds given tolerance (max angle: $(SPIKEANGLE) degrees)
    -> Errors (output)
Errors (output)
Note: Add an error
AttributeCreator_2
    ATTR_TABLE:
      SET_TO error_name = FeatureHasSpikes
      SET_TO details = Feature cannot contain spikes that exceeds given tolerance (max angle: $(SPIKEANGLE) degrees)
    -> IssueLocations (output)
IssueLocations (output)

FME custom transformer ValidateAttributes
This transformer validated all quality problems related to attribute information of the CityGML Building dataset. 
Input: CityGML dataset containing Buildings with all necessary attribute fields defined in OGC CityGML Encoding standard
Output: Table containing all attribute problems of the features

Parameters:
- FME_DATASET = @Value(fme_dataset)   # Fme Dataset
- FME_FEATURE_TYPE = @Value(fme_feature_type)   # Fme Feature Type
- FID = @Value(fid)   # fid
- FME_GEOMETRY = @Value(fme_geometry)   # Fme Geometry
- ROOFTYPE = @Value(roofType)   # roofType

Input (input)
    -> AttributeExposer
Note: Expose attributes
AttributeExposer
    ATTR_LIST = function,usage,roofType,class
    -> GeometryPropertyExtractor
GeometryPropertyExtractor
    EXTRACTTYPE_PARAM = Traits
    PREFIX_EXTRACTED_TRAITS = No
    TRAIT_ATTR_LIST = cityjson_lod,No
    EXTRACTED -> CoordinateSystemRemover
    UNTOUCHED -> CoordinateSystemRemover
CoordinateSystemRemover
    -> GeometryRemover
GeometryRemover
    -> FeatureTypeFilter
    -> AttributeValidator_2
Note: Filter 1st-level and 2nd-level city objects
FeatureTypeFilter
    ATTRIBUTES = <Blank>,<Unfiltered>,Building,BuildingPart,BuildingInstallation
    Building -> FeatureMerger [SUPPLIER]
    BuildingPart -> Tester
    BuildingPart -> FeatureMerger_2 [SUPPLIER]
    BuildingInstallation -> Tester
    BuildingInstallation -> FeatureMerger_2 [SUPPLIER]
AllAttributeErrors (output)

Bookmark: Check all attributes
Note: This transformer checks all attributes. / The default criteria are based on OGC CityJSON standard and recommendations of SIG3D Modelling Guide for 3d Objects Part 2 / Note: FME might warn about incomplete transformer, but that is okay.
AttributeValidator_2
    TABLE = usage,roofType,function,class;ATTRIBUTE_HAS_A_VALUE;<Unused>/roofType,usage,function,class;TYPE;ALPHANUM/roofType;RANGE;[1000,1130]/usage,function;RANGE;[0,2700]/class;RANGE;[1000,1180]
    FAILED -> AttributeKeeper_2
Note: Remove attributes after validation
AttributeKeeper_2
    CREATE_BULK_MODE_FEATURES = NO
    KEEP_ATTRS = fme_dataset,fid
    KEEP_LIST = _fme_validation_message_list{}
    -> ListExploder_4
Note: Find all errors
ListExploder_4
    ATTR_ACCUM_MODE = Merge List Attributes
    ATTR_CONFLICT_RES = Use List Attribute Values
    LIST_ATTR = _fme_validation_message_list{}
    ELEMENTS -> StringSearcher
Note: Find all invalid attributes
StringSearcher
    CASE = no
    MATCHED_RESULT_ATTR = _first_match
    REGEXP = '(.*?)'
    STRING_TO_SEARCH = @Value(_fme_validation_message_list)
    MATCHED -> TestFilter
Note: Filter errors based on its type
TestFilter
    DEFAULT_VALUE = <UNFILTERED>
    PASSED_TEST_GROUP_OUTPUT = FIRST
    TEST_LIST = "BOOL_OP,OR,COMPOSITE_TEST,""""""1"""""",TEST_CLAUSE,CASE_INSENSITIVE_TEST @Value(_fme_validation_message_list) CONTAINS Has a value",@Value(_fme_validation_message_list) CONTAINS Has a value,"BOOL_OP,OR,COMPOSITE_TEST,""""""1"""""",TEST_CLAUSE,CASE_INSENSITIVE_TEST @Value(_fme_validation_message_list) CONTAINS Type is",@Value(_fme_validation_message_list) CONTAINS Type is,"BOOL_OP,OR,COMPOSITE_TEST,""""""1"""""",TEST_CLAUSE,CASE_INSENSITIVE_TEST @Value(_fme_validation_message_list) CONTAINS In range",@Value(_fme_validation_message_list) CONTAINS In range
    @Value(_fme_validation_message_list) CONTAINS Has a value -> Aggregator
    @Value(_fme_validation_message_list) CONTAINS Type is -> Aggregator_3
    @Value(_fme_validation_message_list) CONTAINS In range -> Aggregator_2
Note: Aggregate similar errors based on fid
Aggregator
    ACCUM_ATTRS_NAME = Drop Incoming Attributes
    COUNT_ATTR = count
    GROUP_BY = fid fme_dataset fme_feature_type _first_match
    MODE = Attributes Only
    SEP = " "
    AGGREGATE -> AttributeCreator_6
Note: Format an errors
AttributeCreator_6
    ATTR_TABLE:
      SET_TO error_name = MissingAttributeValue
      SET_TO details = Following attributes are missing: @Value(_first_match)
      SET_TO severity_level = NOTE
    -> AllAttributeErrors (output)
Aggregator_3
    ACCUM_ATTRS_NAME = Drop Incoming Attributes
    COUNT_ATTR = count
    GROUP_BY = fid fme_dataset fme_feature_type _first_match
    MODE = Attributes Only
    SEP = " "
    AGGREGATE -> AttributeCreator_7
AttributeCreator_7
    ATTR_TABLE:
      SET_TO error_name = WrongDataType
      SET_TO details = The following attributes has wrong data type: @Value(_first_match)
      SET_TO severity_level = NOTE
    -> AllAttributeErrors (output)
Aggregator_2
    ACCUM_ATTRS_NAME = Drop Incoming Attributes
    COUNT_ATTR = count
    GROUP_BY = fme_dataset fid fme_feature_type _first_match
    MODE = Attributes Only
    SEP = " "
    AGGREGATE -> AttributeCreator_8
AttributeCreator_8
    ATTR_TABLE:
      SET_TO error_name = ValueNotInAllowedRange
      SET_TO details = The following values are not in allowed range: @Value(_first_match)
      SET_TO severity_level = NOTE
    -> AllAttributeErrors (output)

Bookmark: Check parent - children connections
Note: Test if 2nd-level city object contain at least one parent value
Tester
    BOOL_OP = OR
    TEST_CLAUSE = TEST cityjson_parents{0} ATTRIBUTE_HAS_A_VALUE ""
    TEST_MODE = TEST
    PASSED -> ListExploder
    FAILED -> AttributeCreator_2
AttributeCreator_2
    ATTR_TABLE:
      SET_TO error_name = MissingParentValue
      SET_TO details = The 2nd-level-city-object has no parent ID
      SET_TO severity_level = FAIL
      SET_TO count = 1
    -> AllAttributeErrors (output)
Note: Convert parent list to attributes
ListExploder
    ATTR_ACCUM_MODE = Merge List Attributes
    ATTR_CONFLICT_RES = Use List Attribute Values
    LIST_ATTR = cityjson_parents{}
    ELEMENTS -> FeatureMerger [REQUESTOR]
Note: Check that every parent value of 2nd-level-city-object match with fid of parental feature
FeatureMerger
    ATTR_ACCUM_MODE = Merge Supplier
    ATTR_CONFLICT_RES = Use Requestor
    IGNORE_NULLS = No
    JOIN_KEYS = @Value(cityjson_parents) @Value(fid) AUTO
    MERGE_TYPE = Attributes Only
    PROCESS_DUPS = NO
    REJECT_NULL_MISSING_KEYS = No
    SUPPLIERS_FIRST = No
    UNMERGED_REQUESTOR -> AttributeCreator_3
    USED_SUPPLIER -> ListExploder_2
Note: Select only features which contain childrens and convert list to attributes
ListExploder_2
    ATTR_ACCUM_MODE = Merge List Attributes
    ATTR_CONFLICT_RES = Use List Attribute Values
    LIST_ATTR = cityjson_children{}
    ELEMENTS -> FeatureMerger_2 [REQUESTOR]
Note: Check that every children value of 1st-level-city-object match with fid of children feature
FeatureMerger_2
    ATTR_ACCUM_MODE = Merge Supplier
    ATTR_CONFLICT_RES = Use Requestor
    IGNORE_NULLS = No
    JOIN_KEYS = @Value(cityjson_children) @Value(fid) AUTO
    MERGE_TYPE = Attributes Only
    PROCESS_DUPS = NO
    REJECT_NULL_MISSING_KEYS = No
    SUPPLIERS_FIRST = No
    UNMERGED_REQUESTOR -> AttributeCreator_4
AttributeCreator_4
    ATTR_TABLE:
      SET_TO error_name = InvalidChildrenValue
      SET_TO details = The children ID of the parent is not valid: children not found among all FIDs
      SET_TO severity_level = NOTE
      SET_TO count = 1
    -> AllAttributeErrors (output)
AttributeCreator_3
    ATTR_TABLE:
      SET_TO error_name = InvalidParentValue
      SET_TO details = The parent ID of 2nd-level-city-object is not valid: parent not found among all FIDs
      SET_TO severity_level = NOTE
      SET_TO count = 1
    -> AllAttributeErrors (output)

FME custom transformer CheckAreaAndVolume

Parameters:
- MIN_AREA = 1   # Minimum area of the surface
- MIN_VOLUME = 1   # Minimum volume of the solid
- FID = @Value(fid)   # fid
- FME_DATASET = @Value(fme_dataset)   # Fme Dataset
- FME_FEATURE_TYPE = @Value(fme_feature_type)   # Fme Feature Type
- FME_GEOMETRY = @Value(fme_geometry)   # Fme Geometry
- FME_TYPE = @Value(fme_type)   # Fme Type

Input (input)
    -> Tester
    -> Tester_2
Note: See, if the MIN_AREA or the MIN_VOLUME has a value. If not, skip the rule.
Tester_2
    BOOL_OP = OR
    TEST_CLAUSE = TEST $(MIN_AREA) != ""
    TEST_MODE = TEST
    PASSED -> GeometryPartExtractor
Note: Extract surfaces
GeometryPartExtractor
    GQUERY:
      for $geom in //geometry
      where $geom/@fme_geometry_name = 'GroundSurface'
      or $geom/@fme_geometry_name = 'RoofSurface'
      or $geom/@fme_geometry_name = 'WallSurface'
      return number($geom/@fme_id)
    EXTRACTED -> AreaCalculator
Note: Calculate the area and the volume
AreaCalculator
    AREA_ATTR = _area
    AREA_TYPE = Plane Area
    MULT = 1
    -> TestIfAreaSmallerThan
Note: Test if the measurements are smaller than the given user parameters
TestIfAreaSmallerThan: Tester
    BOOL_OP = OR
    TEST_CLAUSE = TEST @Value(_area) > $(MIN_AREA)
    TEST_MODE = TEST
    FAILED -> Aggregator
    FAILED -> AttributeCreator_3
Note: Aggregate erros to under single fid
Aggregator
    ACCUM_ATTRS_NAME = Drop Incoming Attributes
    COUNT_ATTR = count
    GROUP_BY = fid fme_dataset fme_feature_type
    MODE = Attributes Only
    SEP = ,
    AGGREGATE -> AttributeCreator_2
Note: Add an error
AttributeCreator_2
    ATTR_TABLE:
      SET_TO error_name = AreaTooSmall
      SET_TO details = The building contain surfaces, which area is smaller than $(MIN_AREA) units
    -> GeometryRemover_2
Note: Add an error
AttributeCreator_3
    ATTR_TABLE:
      SET_TO error_name = AreaTooSmall
      SET_TO details = The building contain surfaces, which area is smaller than $(MIN_AREA) units
    -> IssueLocations (output)
Tester
    BOOL_OP = OR
    TEST_CLAUSE = TEST $(MIN_VOLUME) != ""
    TEST_MODE = TEST
    PASSED -> GeometryFilter
GeometryFilter
    BREAK_AGG = No
    GEOM_PORT_NAMES = Solid
    SOLID -> VolumeCalculator
VolumeCalculator
    MULT = 1
    SET_TRAIT = No
    VOLUME_ATTR = _volume
    -> TestIfVolumeSmallerThan
TestIfVolumeSmallerThan: Tester
    BOOL_OP = OR
    TEST_CLAUSE = TEST @Value(_volume) > $(MIN_VOLUME)
    TEST_MODE = TEST
    FAILED -> AttributeCreator_7
AttributeCreator_7
    ATTR_TABLE:
      SET_TO error_name = TooSmallVolume
      SET_TO details = Volume of the feature cannot be smaller than $(MIN_VOLUME) units
    -> GeometryRemover_2
    -> IssueLocations (output)
Note: Remove geometries
GeometryRemover_2
    -> AttributeRemover_4
AttributeRemover_4
    REMOVE_ATTRS = _volume,_area,_vertexcount
    -> Errors (output)
Errors (output)
IssueLocations (output)
