FME workspace QualitySoftwareCityGML.fmw

Parameters:
- CHECK_NORMALS =
- COORD_PREC =
- DestDataset_CITYGML =
- INPUT_CITYGML3 =
- MIN_AREA =
- MIN_VOLUME =
- OUTPUT_CRS =
- OUTPUT_CSV =
- OVERLAP =
- PLAN_ANG =
- PLAN_DIST =
- RULE_CATEGORIES =
- SPIKE_ANGLE =
- TOLERANCE =
- Transformer_parameters =

Readers:
- CITYGML_1: CITYGML from $(INPUT_CITYGML3)

Writers:
- CSV2_1: CSV2 to C:\Users\ATURUNEN\Work Folders\FME+DB
- CITYGML_2: CITYGML to $(DestDataset_CITYGML)

Note: Check rule categories
Tester_2
    BOOL_OP = OR
    COMPOSITE_TEST = 1
    TEST_CLAUSE = CASE_INSENSITIVE_TEST $(RULE_CATEGORIES) CONTAINS ValidateGeometry
    TEST_MODE = CASE_INSENSITIVE_TEST
    PASSED -> ValidateGeometry [GeometryValidatorInput]
ValidateGeometry
    CHECK_NORMALS = $(CHECK_NORMALS)
    FME_DATASET = @Value(fme_dataset)
    FME_FEATURE_TYPE = @Value(fme_feature_type)
    FME_TYPE = @Value(fme_type)
    GML_ID = @Value(gml_id)
    GML_PARENT_ID = @Value(gml_parent_id)
    MIN_AREA = $(MIN_AREA)
    MIN_VOLUME = $(MIN_VOLUME)
    OVERLAP = $(OVERLAP)
    PLAN_ANG = $(PLAN_ANG)
    PLAN_DIST = $(PLAN_DIST)
    SPIKE_ANGLE = $(SPIKE_ANGLE)
    TOLERANCE = $(TOLERANCE)
    TabularErrors -> AttributeKeeper_2
    ErrorsWithGeometry -> Tester_7
Tester_5
    BOOL_OP = OR
    COMPOSITE_TEST = 1
    TEST_CLAUSE = CASE_INSENSITIVE_TEST $(RULE_CATEGORIES) CONTAINS ValidateXlinks
    TEST_MODE = CASE_INSENSITIVE_TEST
    PASSED -> ValidateXlinks
ValidateXlinks
    CITYGML_FEATURE_ROLE = @Value(citygml_feature_role)
    FME_DATASET = @Value(fme_dataset)
    FME_FEATURE_TYPE = @Value(fme_feature_type)
    GML_ID = @Value(gml_id)
    GML_PARENT_ID = @Value(gml_parent_id)
    Errors -> AttributeKeeper_2
Tester_4
    BOOL_OP = OR
    COMPOSITE_TEST = 1
    TEST_CLAUSE = CASE_INSENSITIVE_TEST $(RULE_CATEGORIES) CONTAINS ValidateAddress
    TEST_MODE = CASE_INSENSITIVE_TEST
    PASSED -> ValidateAddress
ValidateAddress
    CITYGML_ADDRESS = @Value(citygml_address)
    FME_DATASET = @Value(fme_dataset)
    FME_FEATURE_TYPE = @Value(fme_feature_type)
    GML_ID = @Value(gml_id)
    GML_PARENT_ID = @Value(gml_parent_id)
    Errors -> AttributeKeeper_2
Tester_3
    BOOL_OP = OR
    COMPOSITE_TEST = 1
    TEST_CLAUSE = CASE_INSENSITIVE_TEST $(RULE_CATEGORIES) CONTAINS ValidateHierarchy
    TEST_MODE = CASE_INSENSITIVE_TEST
    PASSED -> ValidateHierarchy
ValidateHierarchy
    CITYGML_FEATURE_ROLE = @Value(citygml_feature_role)
    FME_DATASET = @Value(fme_dataset)
    FME_FEATURE_TYPE = @Value(fme_feature_type)
    GML_ID = @Value(gml_id)
    GML_PARENT_ID = @Value(gml_parent_id)
    Errors -> AttributeKeeper_2
Tester
    BOOL_OP = OR
    COMPOSITE_TEST = 1
    TEST_CLAUSE = CASE_INSENSITIVE_TEST $(RULE_CATEGORIES) CONTAINS ValidateAttributes
    TEST_MODE = TEST
    PASSED -> ValidateAttributes
ValidateAttributes
    CITYGML_ADDRESS = @Value(citygml_address)
    CITYGML_CLASS = @Value(citygml_class)
    CITYGML_FEATURE_ROLE = @Value(citygml_feature_role)
    CITYGML_MEASURED_HEIGHT = @Value(citygml_measured_height)
    CITYGML_MEASURED_HEIGHT_UNITS = @Value(citygml_measured_height_units)
    CITYGML_RELATIVE_TO_TERRAIN = @Value(citygml_relative_to_terrain)
    CITYGML_RELATIVE_TO_WATER = @Value(citygml_relative_to_water)
    CITYGML_ROOF_TYPE = @Value(citygml_roof_type)
    CITYGML_STOREYS_ABOVE_GROUND = @Value(citygml_storeys_above_ground)
    CITYGML_STOREYS_BELOW_GROUND = @Value(citygml_storeys_below_ground)
    CITYGML_STOREY_HEIGHTS_ABOVE_GROUND = @Value(citygml_storey_heights_above_ground)
    CITYGML_STOREY_HEIGHTS_ABOVE_GROUND_UNITS = @Value(citygml_storey_heights_above_ground_units)
    CITYGML_STOREY_HEIGHTS_BELOW_GROUND = @Value(citygml_storey_heights_below_ground)
    CITYGML_STOREY_HEIGHTS_BELOW_GROUND_UNITS = @Value(citygml_storey_heights_below_ground_units)
    CITYGML_TERMINATIONDATE = @Value(citygml_terminationDate)
    CITYGML_YEAR_OF_CONSTRUCTION = @Value(citygml_year_of_construction)
    CITYGML_YEAR_OF_DEMOLITION = @Value(citygml_year_of_demolition)
    FME_BASENAME = @Value(fme_basename)
    FME_DATASET = @Value(fme_dataset)
    FME_FEATURE_TYPE = @Value(fme_feature_type)
    FME_TYPE = @Value(fme_type)
    GML_ID = @Value(gml_id)
    GML_NAME = @Value(gml_name)
    GML_PARENT_ID = @Value(gml_parent_id)
    Errors -> AttributeKeeper_2

Bookmark: Input data from folder
WallSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer, Area xml_buffer, FaceUUID xml_buffer, ZMax xml_buffer, ZMaxASL xml_buffer, ZMin xml_buffer, ZMinASL xml_buffer
    -> Junction_2
RoofSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer, Area xml_buffer, FaceUUID xml_buffer, RoofOrientation xml_buffer, RoofPitch xml_buffer, ZMax xml_buffer, ZMaxASL xml_buffer, ZMin xml_buffer, ZMinASL xml_buffer
    -> Junction_2
GroundSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer, Area xml_buffer, FaceUUID xml_buffer, ZMin xml_buffer, ZMinASL xml_buffer
    -> Junction_2
BuildingPart (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, BREC_BuildingHeightNN xml_buffer, BREC_RoofNames xml_buffer, CODE xml_buffer, C_KAYTTARK xml_buffer, GroundLevel xml_buffer, HighestRoof xml_buffer, ID xml_buffer, KG_KRAKENN xml_buffer, Katuosoite xml_buffer, Kayttotarkoitus xml_buffer, Kerroksia xml_buffer, Kerrosala xml_buffer, Kokonaisala xml_buffer, LowestRoof xml_buffer, RATU xml_buffer, REPAIRED xml_buffer, Rakennuksen_tila xml_buffer, Rakennusaine xml_buffer, TILA_KOODI xml_buffer, Tilavuus xml_buffer,
      UUID xml_buffer, VTJ_PRT xml_buffer, Valmistunut xml_buffer
    -> Junction_2
Building (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, BREC_BuildingHeightNN xml_buffer, BREC_RoofNames xml_buffer, CODE xml_buffer, C_KAYTTARK xml_buffer, GroundLevel xml_buffer, HighestRoof xml_buffer, ID xml_buffer, KG_KRAKENN xml_buffer, Katuosoite xml_buffer, Kayttotarkoitus xml_buffer, Kerroksia xml_buffer, Kerrosala xml_buffer, Kokonaisala xml_buffer, LowestRoof xml_buffer, RATU xml_buffer, REPAIRED xml_buffer, Rakennuksen_tila xml_buffer, Rakennusaine xml_buffer, TILA_KOODI xml_buffer, Tilavuus xml_buffer,
      UUID xml_buffer, VTJ_PRT xml_buffer, Valmistunut xml_buffer
    -> Junction_2
Junction_2
    -> CheckFmeType
Address (reader CITYGML_1)
    attributes: citygml_target_uri xml_buffer, citygml_feature_role xml_buffer, citygml_feature_role_attr_name xml_buffer, citygml_feature_role_attr_val xml_buffer, gml_description xml_buffer, gml_name xml_buffer, citygml_address xml_xml
    -> DuplicateIDFilter
CityModel (reader CITYGML_1)
    attributes: citygml_target_uri xml_buffer, gml_description xml_buffer, gml_name xml_buffer, citygml_city_object_member{}.xlink_href xml_buffer, citygml_appearance_member{}.xlink_href xml_buffer, gml_feature_member{}.xlink_href xml_buffer
    -> DuplicateIDFilter
    -> Tester_7

Bookmark: Clean the data and find duplicates
Note: Remove features with null geometry
CheckFmeType: Tester
    BOOL_OP = OR
    COMPOSITE_TEST = 1
    TEST_CLAUSE = TEST @Value(fme_type) != fme_no_geom
    TEST_MODE = TEST
    PASSED -> FindDuplicateGeometries
    FAILED -> AttributeCreator_4
Note: Remove duplicate geometries
FindDuplicateGeometries: Matcher
    CHECK_COORDINATE_SYSTEMS = No
    LENIENT_MATCH = Yes
    MATCH = 3D
    MATCHED -> AttributeCreator_2
    SINGLE_MATCHED -> Junction_3
    NOT_MATCHED -> Junction_3
AttributeCreator_2
    ATTR_TABLE:
      SET_TO error_name = DuplicateGeometry
      SET_TO details = Geometry of the feature is not unique
      SET_TO severity_level = FAIL
      SET_TO count = 1
    -> AttributeKeeper_2
    -> Tester_7
Junction_3
    -> DuplicateIDFilter
AttributeCreator_4
    ATTR_TABLE:
      SET_TO error_name = MissingFmeType
      SET_TO details = The feature does not have fme_type ie. it contain no points.
      SET_TO severity_level = FAIL
      SET_TO count = 1
    -> AttributeKeeper_2
Note: Remove features with duplicate IDs
DuplicateIDFilter: DuplicateFilter
    INPUT_ORDERED_CHOICE = No
    KEYATTR = gml_id
    UNIQUE -> AttributeKeeper
    DUPLICATE -> AttributeCreator_3
AttributeKeeper
    CREATE_BULK_MODE_FEATURES = NO
    KEEP_ATTRS = citygml_class,citygml_measured_height,citygml_measured_height_units,citygml_relative_to_terrain,citygml_relative_to_water,citygml_roof_type,citygml_storey_heights_above_ground,citygml_storey_heights_above_ground_units,citygml_storey_heights_below_ground,citygml_storey_heights_below_ground_units,citygml_storeys_above_ground,citygml_storeys_below_ground,citygml_terminationDate,citygml_year_of_construction,citygml_year_of_demolition,fme_basename,fme_dataset,fme_feature_type,fme_type,gml_id,gml_name,gml_parent_id,citygml_feature_role,citygml_address
    KEEP_LIST = citygml_address{} citygml_address{}.xlink_href citygml_bounded_by{} citygml_bounded_by{}.xlink_href citygml_consists_of_building_part{} citygml_consists_of_building_part{}.xlink_href citygml_function{} citygml_function{}.codeSpace citygml_level_of_detail{} citygml_usage{} citygml_usage{}.codeSpace
    -> AppearanceRemover
Note: Remove appearances
AppearanceRemover
    SIDE_TO_REMOVE = Front and Back Sides
    -> ValidateCRS
    UNMATCHED -> ValidateCRS
    <REJECTED> -> ValidateCRS
Note: Validate (and set) coordinate reference systems
ValidateCRS
    COORD_PREC = $(COORD_PREC)
    CRS = $(OUTPUT_CRS)
    FME_DATASET = @Value(fme_dataset)
    FME_FEATURE_TYPE = @Value(fme_feature_type)
    FME_TYPE = @Value(fme_type)
    GML_ID = @Value(gml_id)
    GML_NAME = @Value(gml_name)
    GML_PARENT_ID = @Value(gml_parent_id)
    Passed -> Tester_5
    Passed -> Tester
    Passed -> Tester_3
    Passed -> Tester_4
    Passed -> Tester_2
    ErrorsWithGeometry -> Tester_7
    TabularErrors -> AttributeKeeper_2
AttributeCreator_3
    ATTR_TABLE:
      SET_TO error_name = DuplicateID
      SET_TO details = The gml_id is not unique among all features in the dataset.
      SET_TO severity_level = FAIL
      SET_TO count = 1
    -> AttributeKeeper_2

Bookmark: Write features with *geometry* errors to CityGML
Note: Check, if OUTPUT_CITYGML is determined in the user parameters. If yes, write results to CityGML
Tester_7
    BOOL_OP = OR
    COMPOSITE_TEST = 1
    TEST_CLAUSE = TEST $(DestDataset_CITYGML) != ""
    TEST_MODE = TEST
    PASSED -> AttributeKeeper_3
AttributeKeeper_3
    CREATE_BULK_MODE_FEATURES = NO
    KEEP_ATTRS = error_name,fme_dataset,fme_feature_type,gml_id,gml_parent_id,severity_level,details,fme_basename,fme_type,count
    KEEP_LIST = citygml_level_of_detail{}
    -> GeometryFilter
Note: Filter points because point can be assigned only to GenericCityObject
GeometryFilter
    BREAK_AGG = No
    GEOM_PORT_NAMES = Point Area Surface Solid Null
    POINT -> AttributeCreator_7
    AREA -> AttributeCreator_5
    SURFACE -> AttributeCreator_5
    SOLID -> AttributeCreator_6
    NULL -> CityModel (writer CITYGML_2)
Note: Create mandatory lod_name attributes
AttributeCreator_7
    ATTR_TABLE:
      SET_TO fme_feature_type = GenericCityObject
      SET_TO citygml_lod_name = lod2Geometry
    -> GeometryPropertySetter_4
Note: Set lod_name attributes to traits
GeometryPropertySetter_4
    OVERWRITE_CHOICE = Yes
    REMOVE_ATTRIBUTE = Yes
    SETTYPE_PARAM = Traits From Attributes
    SRC_ATTRS = citygml_lod_name
    SET -> GenericCityObject (writer CITYGML_2)
GenericCityObject (writer CITYGML_2)
    attributes: severity_level xml_char(200), count xml_uint32, error_name xml_char(200), details xml_char(200), citygml_level_of_detail{} xml_buffer
AttributeCreator_5
    ATTR_TABLE = SET_TO citygml_lod_name = lod2MultiSurface
    -> GeometryPropertySetter_2
GeometryPropertySetter_2
    OVERWRITE_CHOICE = Yes
    REMOVE_ATTRIBUTE = Yes
    SETTYPE_PARAM = Traits From Attributes
    SRC_ATTRS = citygml_lod_name
    SET -> FeatureTypeFilter_2
AttributeCreator_6
    ATTR_TABLE = SET_TO citygml_lod_name = lod2Solid
    -> GeometryPropertySetter_3
GeometryPropertySetter_3
    OVERWRITE_CHOICE = Yes
    REMOVE_ATTRIBUTE = Yes
    SETTYPE_PARAM = Traits From Attributes
    SRC_ATTRS = citygml_lod_name
    SET -> FeatureTypeFilter_2
FeatureTypeFilter_2
    ATTRIBUTES = <Blank>,<Unfiltered>,WallSurface,RoofSurface,GroundSurface,BuildingPart,Building,CityModel,Address
    WallSurface -> WallSurface (writer CITYGML_2)
    RoofSurface -> RoofSurface (writer CITYGML_2)
    GroundSurface -> GroundSurface (writer CITYGML_2)
    BuildingPart -> BuildingPart (writer CITYGML_2)
    Building -> Building (writer CITYGML_2)
WallSurface (writer CITYGML_2)
    attributes: count xml_uint32, error_name xml_buffer, details xml_buffer, severity_level xml_char(200), citygml_level_of_detail{} xml_buffer
RoofSurface (writer CITYGML_2)
    attributes: count xml_uint32, error_name xml_buffer, details xml_buffer, severity_level xml_char(200), citygml_level_of_detail{} xml_buffer
GroundSurface (writer CITYGML_2)
    attributes: severity_level xml_char(200), count xml_uint32, error_name xml_char(200), details xml_char(200), citygml_level_of_detail{} xml_buffer
BuildingPart (writer CITYGML_2)
    attributes: severity_level xml_char(200), count xml_uint32, error_name xml_char(200), details xml_char(200), citygml_level_of_detail{} xml_buffer
Building (writer CITYGML_2)
    attributes: severity_level xml_char(200), count xml_uint32, error_name xml_char(200), details xml_char(200), citygml_level_of_detail{} xml_buffer
CityModel (writer CITYGML_2)
    attributes: severity_level xml_char(200), count xml_uint32, error_name xml_char(200), details xml_char(200), citygml_level_of_detail{} xml_buffer

Bookmark: Group and clean errors. Save all errors to CSV file.
AttributeKeeper_2
    CREATE_BULK_MODE_FEATURES = NO
    KEEP_ATTRS = error_name,fme_dataset,fme_feature_type,gml_id,gml_parent_id,severity_level,details,fme_basename,fme_type,count
    -> NullAttributeMapper
NullAttributeMapper
    ATTRCHOICE = Selected Attributes
    ATTRLIST = count
    NEW_VALUE = 1
    NULL_TREATMENT = New Value
    SOURCE_ATTR_VAL = Null Empty "Missing (Selected Attributes Only)"
    -> GeometryRemover
GeometryRemover
    -> ErrorsPerFeature
    -> ErrorsPerDataset
Note: All errors aggregated by their dataset
ErrorsPerDataset: StatisticsCalculator
    CALCULATION_MODE = NUMERIC
    FEAT_STATS = count,NUMERIC_MODE,,,,SUM,,,,,,,,,
    GROUP_BY = error_name fme_dataset details severity_level
    SUMMARY -> Inspector
    SUMMARY -> Tester_6
Note: Check, if OUTPUT_CSV is determined in the user parameters.
Tester_6
    BOOL_OP = OR
    COMPOSITE_TEST = 1
    TEST_CLAUSE = TEST $(OUTPUT_CSV) != ""
    TEST_MODE = TEST
    PASSED -> FilenamePartExtractor_2
FilenamePartExtractor_2
    DIRNAME_ATTR = _dirname
    DIRPATH_ATTR = _dirpath
    EXTENSION_ATTR = _extension
    FULLNAME_ATTR = _filename
    ROOTNAME_ATTR = _rootname
    SRC_ATTR = $(OUTPUT_CSV)
    -> File1 (writer CSV2_1)
File1 (writer CSV2_1)
    attributes: details string, error_name string, error_count string, severity_level string, dataset string
Note: Click to see resuls:
Inspector
ErrorsPerFeature: StatisticsCalculator
    CALCULATION_MODE = NUMERIC
    FEAT_STATS = count,NUMERIC_MODE,,,,SUM,,,,,,,,,
    GROUP_BY = gml_id error_name details severity_level fme_dataset fme_feature_type gml_parent_id
    SUMMARY -> Aggregator
Note: All errors aggregated by feature. One feature might contain same error multiple times.
Aggregator
    ACCUM_ATTRS_NAME = Drop Incoming Attributes
    CONCAT_ATTRS = details error_name severity_level
    GROUP_BY = gml_id
    MODE = Attributes Only
    SEP = " & "
    SUM = count.sum
    AGGREGATE -> Inspector_3
Note: Click to see resuls:
Inspector_3

FME custom transformer GroundOverlappingIn2D
Thia transformer check if two GroundSurfaces are overlapping each other when forced to 2D.

Parameters:
- FME_DATASET =
- FME_FEATURE_TYPE =
- FME_TYPE =
- GML_PARENT_ID =
- ID =
- OVERLAP =

Input (input)
    -> Tester
Note: See, if the OVERLAP has a value. If not, skip the rule.
Tester
    BOOL_OP = OR
    COMPOSITE_TEST = 1
    TEST_CLAUSE = TEST $(OVERLAP) != ""
    TEST_MODE = TEST
    PASSED -> FeatureTypeFilter
Note: Select only GroundSurfaces
FeatureTypeFilter
    ATTRIBUTES = <Blank>,<Unfiltered>,GroundSurface,Building
    Building -> SurfaceFootprintReplacer
Note: Force to 2D by replacing geometry by its footprint
SurfaceFootprintReplacer
    OFFSET_Z = 0
    SHADOW_MODE = Overhead Shadow
    FOOTPRINT -> GeometryValidator
Note: Fix self-intersection bercause otherwise they would cause unintentional overlap.
GeometryValidator
    ISSUE_ATTR_NAME = _issues
    PRESETS = Custom
    REPAIR = Yes
    RULES = SELF_INTERSECTING CHECK_HOLE_TOUCHING_POLYGON]No]CONNECT_Z_MODE_SI]FIRST_WINS]SELF_INTERSECTION_TOLERANCE]None]INTERSECT_ACROSS_MULTIS]No]FME_CONTROLLER_QUERY_FILE]transformers/dependencies/geometryvalidator8/SELF_INTERSECTING.fme]FME_CONTROLLER_CHOICE]SELF_INTERSECTING
    SUMMARY = None
    PASSED -> AreaCalculator
    REPAIRED -> AreaCalculator
Note: Calculate area for each footprint
AreaCalculator
    AREA_ATTR = _original_area
    AREA_TYPE = Plane Area
    MULT = 1
    -> AreaOnAreaOverlayer [AREA]
    -> Aggregator_2
Note: Find overlapping areas. / Add gml_id of the overlapping parts to the list called overlap
AreaOnAreaOverlayer
    ACCUM_ATTRS_NAME = Use Attributes From One Feature
    CLEANING_TOLERANCE = Automatic
    CONNECT_Z_MODE = First Wins
    DEAGGREGATE_INPUT = Yes
    LIST_ATTRS_TO_INCLUDE = gml_id
    LIST_NAME = overlaps
    OVC_ATTR = _overlaps
    AREA -> Tester_5
Note: Select only parts which are overlapping
Tester_5
    BOOL_OP = OR
    COMPOSITE_TEST = 1
    TEST_CLAUSE = TEST @Value(_overlaps) > 1
    TEST_MODE = TEST
    PASSED -> ExpressionEvaluator_2
Note: Subtract one from _overlaps parameters
ExpressionEvaluator_2
    ACTION = Create New Attribute
    EXPRESSION = @Value(_overlaps)-1
    VAL_ATTR = _overlaps
    -> ListSearcher
Note: Find gml_id of the one overlapping part.
ListSearcher
    ATTR_VALUE = @Value(gml_id)
    INDEX_ATTR = _list_index
    LIST_ATTR = overlaps{}.gml_id
    MATCHTYPE = FIRST_MATCHED_ENCODED
    FOUND -> ListExploder_3
Note: Create a duplicate with anothergml_id to aggregate it to both pieces of GroundSurfaces, which are overlapping.
ListExploder_3
    ATTR_ACCUM_MODE = Merge List Attributes
    ATTR_CONFLICT_RES = Use List Attribute Values
    LIST_ATTR = overlaps{}
    ELEMENTS -> Aggregator_2
Note: Aggregate overlapping parts to original footprints
Aggregator_2
    ACCUM_ATTRS_NAME = Merge Incoming Attributes
    AGGREGATE_TYPE = Homogeneous Collection (If Possible)
    GROUP_BY = gml_id
    MODE = Geometry - Assemble One Level
    SEP = ,
    SUM = _overlaps
    AGGREGATE -> AreaCalculator_3
Note: Calculate an area which contain extra overlapping parts
AreaCalculator_3
    AREA_ATTR = _overlapping_area
    AREA_TYPE = Plane Area
    MULT = 1
    -> ExpressionEvaluator
Note: Calculate overlapping percentage by comparing original area to new area
ExpressionEvaluator
    ACTION = Create New Attribute
    EXPRESSION = (@Value(_overlapping_area)/@Value(_original_area)-1)*100
    VAL_ATTR = _overlap_percentage
    -> TestFilter_2
Note: Compare overlapping percentage to threshold specified in the user parameters.
TestFilter_2
    DEFAULT_VALUE = <UNFILTERED>
    TEST_LIST = "BOOL_OP,OR,COMPOSITE_TEST,""""""1"""""",TEST_CLAUSE,TEST @Value(_overlap_percentage) > $(OVERLAP)",OverlapOverThreshold
    OverlapOverThreshold -> AttributeCreator_2
Note: If overlapping percentage is more than threshold, add an error.
AttributeCreator_2
    ATTR_TABLE:
      SET_TO error_name = GroundOverlappingIn2D
      SET_TO details = The geometry of two or more GroundSurfaces cannot overlap more than $(OVERLAP) % of their areas.
    -> GeometryRemover
    -> IssueLocations (output)
IssueLocations (output)
GeometryRemover
    -> CoordinateSystemRemover
CoordinateSystemRemover
    -> OverlapErrors (output)
OverlapErrors (output)

FME custom transformer CheckAreaAndVolume
This transformer checks minimum values for areas and volumes.

Parameters:
- FME_DATASET =
- FME_FEATURE_TYPE =
- FME_TYPE =
- GML_ID =
- GML_PARENT_ID =
- MIN_AREA =
- MIN_VOLUME =

Input (input)
    -> Tester_2
    -> Tester
Note: See, if the MIN_AREA or the MIN_VOLUME has a value. If not, skip the rule.
Tester_2
    BOOL_OP = OR
    COMPOSITE_TEST = 1
    TEST_CLAUSE = TEST $(MIN_AREA) != ""
    TEST_MODE = TEST
    PASSED -> GeometryFilter_2
Note: Filter geometries
GeometryFilter_2
    BREAK_AGG = No
    GEOM_PORT_NAMES = Surface
    SURFACE -> Deaggregator_2
Note: Flatten surface features t o faces
Deaggregator_2
    ATTR_ACCUM_MODE = Merge List Attributes
    ATTR_CONFLICT_RES = Use List Attribute Values
    EXPLODE_INSTANCES = No
    LIST_ATTR_MODE_LOOKUP = LEAN
    MODE = Flatten One Level
    SPLIT_COMPOSITES = Yes
    DEAGGREGATED -> AreaCalculator_2
Note: Calculate area and volume
AreaCalculator_2
    AREA_ATTR = _area
    AREA_TYPE = Plane Area
    MULT = 1
    -> TestIfAreaSmallerThan_2
Note: Test if measurements are smaller than given user parameters
TestIfAreaSmallerThan_2: Tester
    BOOL_OP = OR
    COMPOSITE_TEST = 1
    TEST_CLAUSE = TEST @Value(_area) > $(MIN_AREA)
    TEST_MODE = TEST
    FAILED -> Aggregator
    FAILED -> AttributeCreator_2
Note: Aggregate erros to under single fid
Aggregator
    ACCUM_ATTRS_NAME = Drop Incoming Attributes
    COUNT_ATTR = count
    GROUP_BY = fme_dataset fme_feature_type gml_id gml_parent_id
    MODE = Attributes Only
    SEP = ,
    AGGREGATE -> AttributeCreator_4
Note: Add an error
AttributeCreator_4
    ATTR_TABLE:
      SET_TO error_name = AreaTooSmall
      SET_TO details = Area of the feature cannot be smaller than $(MIN_AREA) units
    -> GeometryRemover_2
Note: Add an error
AttributeCreator_2
    ATTR_TABLE:
      SET_TO error_name = AreaTooSmall
      SET_TO details = Area of the feature cannot be smaller than $(MIN_AREA) units
    -> IssueLocations (output)
Tester
    BOOL_OP = OR
    COMPOSITE_TEST = 1
    TEST_CLAUSE = TEST $(MIN_VOLUME) != ""
    TEST_MODE = TEST
    PASSED -> GeometryFilter
GeometryFilter
    BREAK_AGG = No
    GEOM_PORT_NAMES = Solid
    SOLID -> VolumeCalculator
VolumeCalculator
    MULT = 1
    SET_TRAIT = No
    VOLUME_ATTR = _volume
    -> TestIfVolumeSmallerThan
TestIfVolumeSmallerThan: Tester
    BOOL_OP = OR
    COMPOSITE_TEST = 1
    TEST_CLAUSE = TEST @Value(_volume) > $(MIN_VOLUME)
    TEST_MODE = TEST
    FAILED -> AttributeCreator_7
AttributeCreator_7
    ATTR_TABLE:
      SET_TO error_name = VolumeTooSmall
      SET_TO details = Volume of the feature cannot be smaller than $(MIN_VOLUME) units
    -> GeometryRemover_2
    -> IssueLocations (output)
Note: Remove geometries
GeometryRemover_2
    -> Errors (output)
Errors (output)
IssueLocations (output)

FME custom transformer SurfaceNormalExtractor
Calculates surface normal vectors on Faces from the average of the existing surface vertex normals. If no vertex normals exist, they will be generated by a GeometryValidator.
Normals will be stored as the following traits on each Face:
surface_normal_x
surface_normal_y
surface_normal_z
The SurfaceNormalExtractor will work on Composite and MultiSurfaces as well, with no need to de-aggregate. Meshes will be automatically converted to Composite Surfaces.
**Input**
Source features
**Output**
Output features with calculated surface normals

Input (input)
    -> GeometryCoercer_2
Note: Convert other surface types / to faced based surface
GeometryCoercer_2
    GQUERY:
      for $geom in //geometry
      where $geom/@fme_geometry_type = 'IFMEMesh'
      or $geom/@fme_geometry_type = 'IFMERectangleFace'
      or $geom/@fme_geometry_type = 'IFMETriangleFan'
      or $geom/@fme_geometry_type = 'IFMETriangleStrip'
      return number($geom/@fme_id)
    KIND = fme_composite_surface
    COERCED -> GeometryValidator
    UNTOUCHED -> GeometryValidator
Note: Generate vertex / normals if needed
GeometryValidator
    ISSUE_ATTR_NAME = _surface_normal_issues
    MISSING_VERTEX_NORMALS = MISSING_VERTEX_NORMALS
    PRESETS = Custom
    REPAIR = Yes
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%SHELL_VALIDATION_PARAMS%"Yes"%SOLID_VOID_REPAIR%""%"Yes"%OGC_SIMPLE_CHECK%""%"No"%OGC_VALID_CHECK%OGC_VALID_PARAMS%"No"%MISSING_TEXTURE_COORDINATES%""%"Yes"%MISSING_VERTEX_NORMALS%""%"Yes"%AREA_ORIENTATION%ORIENTATION_CHECK_PARAMS%"Yes"
    SUMMARY = None
    PASSED -> GeometryPropertySetter
    REPAIRED -> GeometryPropertySetter
Note: Create Face ids
GeometryPropertySetter
    CNT_ATTR = _surface_normal_id
    DOMAIN = _surface_normal_id
    GQUERY:
      for $geom in //geometry
      where $geom/@fme_geometry_type = 'IFMEFace'
      return number($geom/@fme_id)
    OVERWRITE_CHOICE = Yes
    SCOPE = Global
    SETTYPE_PARAM = Traits From Counter
    START = 0
    SET -> GeometryPartExtractor
    SET -> GeometryPropertySetter_UNTOUCHED_-__TraitMerger_REQUESTOR
    UNTOUCHED -> GeometryPropertySetter_UNTOUCHED_-__TraitMerger_REQUESTOR
GeometryPropertySetter_UNTOUCHED_-__TraitMerger_REQUESTOR: Junction
    -> TraitMerger [REQUESTOR]
Note: Extract Faces
GeometryPartExtractor
    EXTRACTTYPE_PARAM = Extract
    GQUERY:
      for $geom in //geometry
      where $geom/@fme_geometry_type = 'IFMEFace'
      return number($geom/@fme_id)
    PROCESSED -> GeometryPropertyExtractor
Note: Extract Face ids
GeometryPropertyExtractor
    EXTRACTTYPE_PARAM = Traits
    PREFIX_EXTRACTED_TRAITS = No
    TRAIT_ATTR_LIST = _surface_normal_id,No
    EXTRACTED -> GeometryCoercer
    UNTOUCHED -> Junction_2
Note: Coerce to polygon / for measure extraction
GeometryCoercer
    GQUERY:
      for $geom in //geometry
      where $geom/count(parent::geometry) = 0
      return number($geom/@fme_id)
    KIND = fme_polygon
    COERCED -> MeasureExtractor
Note: Extract normal measures
MeasureExtractor
    GEOM_TYPE = Whole Area
    MEASURE_LIST = fme_vertex_normal_x
    MEASURE_NAME = fme_vertex_normal_x
    -> MeasureExtractor_2
    <REJECTED> -> Junction_3
MeasureExtractor_2
    GEOM_TYPE = Whole Area
    MEASURE_LIST = fme_vertex_normal_y
    MEASURE_NAME = fme_vertex_normal_y
    -> MeasureExtractor_3
    <REJECTED> -> Junction_3
MeasureExtractor_3
    GEOM_TYPE = Whole Area
    MEASURE_LIST = fme_vertex_normal_z
    MEASURE_NAME = fme_vertex_normal_z
    -> ListSummer
    <REJECTED> -> Junction_3
Note: Sum normal measures
ListSummer
    RESULT = _normal_sum_x
    SRC_LIST = fme_vertex_normal_x{}
    -> ListSummer_2
ListSummer_2
    RESULT = _normal_sum_y
    SRC_LIST = fme_vertex_normal_y{}
    -> ListSummer_3
ListSummer_3
    RESULT = _normal_sum_z
    SRC_LIST = fme_vertex_normal_z{}
    -> ListElementCounter
Note: Count normal measures
ListElementCounter
    CNT_ATTR = _normal_count_x
    LIST_NAME = fme_vertex_normal_x{}
    -> ListElementCounter_2
ListElementCounter_2
    CNT_ATTR = _normal_count_y
    LIST_NAME = fme_vertex_normal_y{}
    -> ListElementCounter_3
ListElementCounter_3
    CNT_ATTR = _normal_count_z
    LIST_NAME = fme_vertex_normal_z{}
    -> AttributeCreator
Note: Calculate surface normal / from average of vertex / normals
AttributeCreator
    ATTR_TABLE:
      SET_TO surface_normal_x = @Evaluate(@Value(_normal_sum_x)/@Value(_normal_count_x))
      SET_TO surface_normal_y = @Evaluate(@Value(_normal_sum_y)/@Value(_normal_count_y))
      SET_TO surface_normal_z = @Evaluate(@Value(_normal_sum_z)/@Value(_normal_count_z))
    -> GeometryPropertySetter_2
Note: Set surface normal as traits
GeometryPropertySetter_2
    OVERWRITE_CHOICE = Yes
    REMOVE_ATTRIBUTE = No
    SETTYPE_PARAM = Traits From Attributes
    SRC_ATTRS = surface_normal_x _surface_normal_id surface_normal_z surface_normal_y
    UNTOUCHED -> AttributeRemover
Note: Remove uneeded attributes
AttributeRemover
    LIST_ATTRS = _surface_normal_issues{} fme_vertex_normal_x{} fme_vertex_normal_y{} fme_vertex_normal_z{}
    REMOVE_ATTRS = _normal_sum_x,surface_normal_x,_normal_sum_y,_normal_count_x,_normal_sum_z,_surface_normal_id,surface_normal_z,surface_normal_y
    -> AttributeKeeper_2
AttributeKeeper_2
    CREATE_BULK_MODE_FEATURES = No
    -> TraitMerger [SUPPLIER]
Note: Merge normal traits on / Faces by Face id
TraitMerger
    ATTR_ACCUM_MODE = Merge Supplier
    ATTR_CONFLICT_RES = Use Requestor
    COMPONENTS_TO_JOIN = _surface_normal_id;_surface_normal_id
    REQUESTOR_TYPE = Trait
    R_GQUERY:
      for $geom in //geometry
      where $geom/@fme_geometry_type = 'IFMEFace'
      return number($geom/@fme_id)
    SUPPLIER_TYPE = Trait
    S_GQUERY:
      for $geom in //geometry
      where $geom/count(parent::geometry) = 0
      return number($geom/@fme_id)
    RESULT -> GeometryPropertyRemover
    UNTOUCHED -> GeometryPropertyRemover
Note: Remove Face id
GeometryPropertyRemover
    REGEX_FILTER = _surface_normal_id
    REMOVETYPE_PARAM = Traits
    REMOVE_ALL = No
    REMOVED -> AttributeRemover_2
    UNTOUCHED -> AttributeRemover_2
Note: Remove uneeded attributes
AttributeRemover_2
    LIST_ATTRS = _surface_normal_issues{}
    -> Output (output)
Output (output)
Junction
    -> Junction_2
Junction_2
    -> Junction_3
Junction_3
    -> Junction_4
Junction_4

FME custom transformer ValidateGeometry
This transformer validates all quality problems related to geometry of the CityGML Building dataset. This contains multiple embedded transformers.
Input: CityGML dataset containing Buildings with coordinate reference system
Output: Table containing all geometry problems of the features

Parameters:
- CHECK_NORMALS =
- FME_DATASET =
- FME_FEATURE_TYPE =
- FME_TYPE =
- GML_ID =
- GML_PARENT_ID =
- MIN_AREA =
- MIN_VOLUME =
- OVERLAP =
- PLAN_ANG =
- PLAN_DIST =
- SPIKE_ANGLE =
- TOLERANCE =
- Transformer_parameters =

Note: Some transformers will modify the data because otherwise it might not be suitable for the rest of rules. Thus the order of transformers is important.
GeometryValidatorInput (input)
    -> Tester_2
Junction
    -> CheckSelfIntersectionsIn2D
    -> Junction_3
    -> CheckAllOtherProblems
    -> CheckAndFixOGC
Junction_3
    -> CheckAreaAndVolume
    -> GroundOverlappingIn2D
    -> CheckNormals
    -> CompareRoofToFloor
    -> CheckSpikes

Bookmark: Prepare geometries (Filter feature types ja geometries, splits multiple geometries and remove unused attributes)
Note: Drop Addresses and CityModels
Tester_2
    BOOL_OP = AND
    COMPOSITE_TEST = 1 AND 2
    TEST_CLAUSE:
      TEST @Value(fme_feature_type) != CityModel
      TEST @Value(fme_feature_type) != Address
    TEST_MODE = TEST
    PASSED -> GeometryFilter_2
GeometryFilter_2
    BREAK_AGG = No
    GEOM_PORT_NAMES = Surface Solid
    SURFACE -> MultipleGeometryFilter
    SOLID -> MultipleGeometryFilter
    <UNFILTERED> -> AttributeCreator_6
MultipleGeometryFilter
    CONTAINS -> Deaggregator
    NOT_CONTAINS -> RemoveInvalidGeometries
    <REJECTED> -> AttributeRemover
Note: Deaggregate multiple geometries
Deaggregator
    ATTR_ACCUM_MODE = Merge List Attributes
    ATTR_CONFLICT_RES = Use List Attribute Values
    EXPLODE_INSTANCES = No
    LIST_ATTR_MODE_LOOKUP = LEAN
    MODE = Flatten One Level
    SPLIT_COMPOSITES = No
    DEAGGREGATED -> RemoveInvalidGeometries
AttributeRemover
    REMOVE_ATTRS = fme_rejection_code
    -> RemoveInvalidGeometries
Note: Fix NaNs, infinities, degenerated and corrupted geometries. Also remove concecutive duplicate points.
RemoveInvalidGeometries: GeometryValidator
    ISSUE_ATTR_NAME = _issues
    PRESETS = Custom
    REPAIR = Yes
    RULES = NAN_REMOVAL PROCESS_MEASURE]YES]FME_CONTROLLER_QUERY_FILE]transformers/dependencies/geometryvalidator/NAN_REMOVAL.fme]FME_CONTROLLER_CHOICE]NAN_REMOVAL TYPE_REPAIR SOURCE]]CONNECT_Z_MODE]FIRST_WINS]ARC_ENDPOINT_TOLERANCE_MODE]Auto]ARC_ENDPOINT_TOLERANCE]0.0]FME_CONTROLLER_QUERY_FILE]transformers/dependencies/geometryvalidator/TYPE_REPAIR.fme]FME_CONTROLLER_CHOICE]TYPE_REPAIR CONSECUTIVE_IDENTICAL_VERTICES_2D CHECK_Z]YES]TOLERANCE]$(TOLERANCE)]FME_CONTROLLER_QUERY_FILE]transformers/dependencies/geometryvalidator/CONSECUTIVE_IDENTICAL_VERTICES_2D.fme]FME_CONTROLLER_CHOICE]CONSECUTIVE_IDENTICAL_VERTICES_2D
    SUMMARY = Brief
    PASSED -> Junction
    REPAIRED -> Junction
    ISSUE_LOCATIONS -> AttributeCreator_FIXED
    INVALID_PARTS -> ListExploder_3
AttributeCreator_6
    ATTR_TABLE:
      SET_TO error_name = GeometryTypeError
      SET_TO details = Geometry of the feature must be either Solid or Surface
    -> ListExploder_3

Bookmark: Embedded transformers
CheckAreaAndVolume
    FME_DATASET = @Value(fme_dataset)
    FME_FEATURE_TYPE = @Value(fme_feature_type)
    FME_TYPE = @Value(fme_type)
    GML_ID = @Value(gml_id)
    GML_PARENT_ID = @Value(gml_parent_id)
    MIN_AREA = $(MIN_AREA)
    MIN_VOLUME = $(MIN_VOLUME)
    Errors -> AttributeCreator_NOTE
    IssueLocations -> ListExploder_3
CompareRoofToFloor
    FME_DATASET = @Value(fme_dataset)
    FME_FEATURE_TYPE = @Value(fme_feature_type)
    GML_ID = @Value(gml_id)
    GML_PARENT_ID = @Value(gml_parent_id)
    IssueLocations -> ListExploder_3
    Errors -> AttributeCreator_NOTE
CheckNormals
    CheckVertexNormals = $(CHECK_NORMALS)
    FME_DATASET = @Value(fme_dataset)
    FME_FEATURE_TYPE = @Value(fme_feature_type)
    FME_TYPE = @Value(fme_type)
    GML_ID = @Value(gml_id)
    GML_PARENT_ID = @Value(gml_parent_id)
    Errors -> AttributeCreator_NOTE
    IssueLocations -> ListExploder_3
CheckSpikes
    FME_DATASET = @Value(fme_dataset)
    FME_FEATURE_TYPE = @Value(fme_feature_type)
    FME_TYPE = @Value(fme_type)
    GML_ID = @Value(gml_id)
    GML_PARENT_ID = @Value(gml_parent_id)
    SPIKE_ANGLE = $(SPIKE_ANGLE)
    Errors -> AttributeCreator_NOTE
    IssueLocations -> ListExploder_3
GroundOverlappingIn2D
    FME_DATASET = @Value(fme_dataset)
    FME_FEATURE_TYPE = @Value(fme_feature_type)
    FME_TYPE = @Value(fme_type)
    GML_PARENT_ID = @Value(gml_parent_id)
    ID = @Value(gml_id)
    OVERLAP = $(OVERLAP)
    IssueLocations -> ListExploder_3
    OverlapErrors -> AttributeCreator_NOTE

Bookmark: Check all rules
CheckAndFixOGC: GeometryValidator
    ISSUE_ATTR_NAME = _issues
    PRESETS = Custom
    REPAIR = Yes
    RULES = OGC_VALID_CHECK OGC_VERSION]V1.2.0]FME_CONTROLLER_QUERY_FILE]transformers/dependencies/geometryvalidator8/OGC_VALID_CHECK.fme]FME_CONTROLLER_CHOICE]OGC_VALID_CHECK]LEGACY_OGC]No OGC_SIMPLE_CHECK FME_CONTROLLER_QUERY_FILE]transformers/dependencies/geometryvalidator8/OGC_SIMPLE_CHECK.fme]FME_CONTROLLER_CHOICE]OGC_SIMPLE_CHECK]LEGACY_OGC]No
    SUMMARY = Detailed
    FAILED -> ListExploder_6
    ISSUE_LOCATIONS -> AttributeCreator_FIXED
    INVALID_PARTS -> ListExploder_3
Note: Explode features because OGC rules do not provide issue locations
ListExploder_6
    ATTR_ACCUM_MODE = Merge List Attributes
    ATTR_CONFLICT_RES = Use List Attribute Values
    LIST_ATTR = _issues{}
    ELEMENTS -> AttributeFilter_3
AttributeFilter_3
    ATTR_NAME = issue_found
    ATTR_VALUES = <Empty>,<Missing>,<Null>,<Unfiltered>,Fails OGC Simple
    <UNFILTERED> -> AttributeCreator_FIXED
    Fails OGC Simple -> AttributeCreator_NOTE
CheckAllOtherProblems: GeometryValidator
    ISSUE_ATTR_NAME = _issues
    PRESETS = Custom
    REPAIR = No
    RULES = AREA_ORIENTATION AREA_ORIENTATION]VALID]FME_CONTROLLER_QUERY_FILE]transformers/dependencies/geometryvalidator8/AREA_ORIENTATION.fme]FME_CONTROLLER_CHOICE]AREA_ORIENTATION MISSING_MEASURES_AND_ELEVATIONS MISSING_VALUES_MODE]SENTINEL]MISSING_MEASURES_MODE]<Unused>]SENTINEL_VALUE]0]LENGTH_DIMENSION]<Unused>]FME_CONTROLLER_QUERY_FILE]transformers/dependencies/geometryvalidator8/MISSING_MEASURES_AND_ELEVATIONS.fme]FME_CONTROLLER_CHOICE]MISSING_MEASURES_AND_ELEVATIONS SURFACE_ORIENTATION FME_CONTROLLER_QUERY_FILE]transformers/dependencies/geometryvalidator8/SURFACE_ORIENTATION.fme]FME_CONTROLLER_CHOICE]SURFACE_ORIENTATION SOLID_ORIENTATION FME_CONTROLLER_QUERY_FILE]transformers/dependencies/geometryvalidator8/SOLID_ORIENTATION.fme]FME_CONTROLLER_CHOICE]SOLID_ORIENTATION PLANAR_SURFACE CHECK_AREA]DO_CHECK_AREA]TOLERANCE_MODE]CUSTOM]TOLERANCE]$(PLAN_DIST)]ANGULAR_TOLERANCE_MODE]CUSTOM]ANGULAR_TOLERANCE]$(PLAN_ANG)]FME_CONTROLLER_QUERY_FILE]transformers/dependencies/geometryvalidator8/PLANAR_SURFACE.fme]FME_CONTROLLER_CHOICE]PLANAR_SURFACE
    SUMMARY = Brief
    ISSUE_LOCATIONS -> AttributeCreator_NOTE
    INVALID_PARTS -> ListExploder_3

Bookmark: Check self-intersections and repair solid boundaries. After that check solid voids
CheckSelfIntersectionsIn2D: GeometryValidator
    ISSUE_ATTR_NAME = _issues
    PRESETS = Custom
    REPAIR = No
    RULES = SELF_INTERSECTING CHECK_HOLE_TOUCHING_POLYGON]No]CONNECT_Z_MODE_SI]FIRST_WINS]SELF_INTERSECTION_TOLERANCE]None]INTERSECT_ACROSS_MULTIS]Yes]FME_CONTROLLER_QUERY_FILE]transformers/dependencies/geometryvalidator8/SELF_INTERSECTING.fme]FME_CONTROLLER_CHOICE]SELF_INTERSECTING
    SUMMARY = Brief
    PASSED -> CheckAndFixSolid
    ISSUE_LOCATIONS -> AttributeCreator_FAIL
    INVALID_PARTS -> ListExploder_3
CheckAndFixSolid: GeometryValidator
    ISSUE_ATTR_NAME = _issues
    PRESETS = Custom
    REPAIR = Yes
    RULES = SHELL_VALIDATION FLIP_APPEARANCE_MODE]FLIP_APPEARANCES]FME_CONTROLLER_QUERY_FILE]transformers/dependencies/geometryvalidator8/SHELL_VALIDATION.fme]FME_CONTROLLER_CHOICE]SHELL_VALIDATION SOLID_VOID_REPAIR FME_CONTROLLER_QUERY_FILE]transformers/dependencies/geometryvalidator8/SOLID_VOID_REPAIR.fme]FME_CONTROLLER_CHOICE]SOLID_VOID_REPAIR
    SUMMARY = Brief
    ISSUE_LOCATIONS -> AttributeFilter
    INVALID_PARTS -> ListExploder_3
AttributeFilter
    ATTR_NAME = issue_found
    ATTR_VALUES = <Empty>,<Missing>,<Null>,<Unfiltered>,Invalid Solid Boundaries
    <UNFILTERED> -> AttributeCreator_NOTE
    Invalid Solid Boundaries -> AttributeCreator_FIXED

Bookmark: Add severity levels and format tabular output results per building
AttributeCreator_FAIL
    ATTR_TABLE = SET_TO severity_level = FAIL
    -> Junction_2
AttributeCreator_NOTE
    ATTR_TABLE = SET_TO severity_level = NOTE
    -> Junction_2
AttributeCreator_FIXED
    ATTR_TABLE = SET_TO severity_level = FIXED
    -> Junction_2
Junction_2
    -> GeometryRemover
GeometryRemover
    -> CoordinateSystemRemover
CoordinateSystemRemover
    -> AttributeManager_3
AttributeManager_3
    ATTR_TABLE:
      SET_TO count = FME_CONDITIONAL:DEFAULT_VALUE'_FME_NO_OP_'BOOL_OP;OR;COMPOSITE_TEST;1;TEST _issues{0}.count ATTRIBUTE_HAS_A_VALUE _FME_BLANK_STRING_'@Value(_issues{0}.count)'BOOL_OP;OR;COMPOSITE_TEST;1;TEST count NOT_ATTRIBUTE_HAS_A_VALUE _FME_BLANK_STRING_'1'BOOL_OP;OR;COMPOSITE_TEST;1;TEST @Value(count) < 1'1'FME_NUM_CONDITIONS4___
      RENAME_SET_DEFAULT details = Miscellaneous
      RENAME_SET_DEFAULT error_name = @Value(issue_found)
      REMOVE issue_found
      REMOVE _volume
    USER_EXPOSED_ATTRIBUTES = fid,fme_geometry
    -> Aggregator
Note: Aggregate under single gml_id
Aggregator
    ACCUM_ATTRS_NAME = Drop Incoming Attributes
    GROUP_BY = details error_name fme_dataset fme_feature_type severity_level gml_id gml_parent_id
    MODE = Attributes Only
    SEP = ,
    SUM = count
    AGGREGATE -> TabularErrors (output)
TabularErrors (output)

Bookmark: Add severity levels and create output containing only geometrical locations of issues
Note: Expose the list of errors
ListExploder_3
    ATTR_ACCUM_MODE = Merge List Attributes
    ATTR_CONFLICT_RES = Use List Attribute Values
    LIST_ATTR = _issues{}
    ELEMENTS -> ListExploder_5
    <REJECTED> -> AttributeManager
Note: Expose details
ListExploder_5
    ATTR_ACCUM_MODE = Merge List Attributes
    ATTR_CONFLICT_RES = Use List Attribute Values
    LIST_ATTR = supplementary_info{}
    ELEMENTS -> AttributeManager
    <REJECTED> -> AttributeManager
Note: Remove and format attributes
AttributeManager
    ATTR_TABLE:
      SET_TO count = FME_CONDITIONAL:DEFAULT_VALUE'_FME_NO_OP_'BOOL_OP;OR;COMPOSITE_TEST;1;TEST count NOT_ATTRIBUTE_HAS_A_VALUE _FME_BLANK_STRING_'1'BOOL_OP;OR;COMPOSITE_TEST;1;TEST @Value(count) < 1'1'FME_NUM_CONDITIONS3___
      RENAME_SET_VALUE issue_found > error_name
      REMOVE location_sample.x
      REMOVE location_sample.y
      REMOVE location_sample.z
      RENAME_SET_DEFAULT supplementary_info > details = FME_CONDITIONAL:DEFAULT_VALUE'_FME_NO_OP_'BOOL_OP;OR;COMPOSITE_TEST;1;TEST details ATTRIBUTE_IS_MISSING _FME_BLANK_STRING_'Miscellanous'FME_NUM_CONDITIONS2___
      REMOVE fme_rejection_code
    USER_EXPOSED_ATTRIBUTES = fid,fme_geometry
    -> AttributeFilter_2
AttributeFilter_2
    ATTR_NAME = error_name
    ATTR_VALUES = <Empty>,<Missing>,<Null>,<Unfiltered>,Self-Intersections in 2D,Invalid Solid Boundaries,Degenerate or Corrupt Geometries,Duplicate Consecutive Points in 3D, Contains NaNs or Infinities,Fails OGC Valid
    <UNFILTERED> -> AttributeCreator_NOTE_2
    Self-Intersections in 2D -> AttributeCreator_FAIL_2
    Invalid Solid Boundaries -> AttributeCreator_FIXED_2
    Degenerate or Corrupt Geometries -> AttributeCreator_FIXED_2
    Duplicate Consecutive Points in 3D -> AttributeCreator_FIXED_2
    Contains NaNs or Infinities -> AttributeCreator_FIXED_2
    Fails OGC Valid -> AttributeCreator_FIXED_2
AttributeCreator_NOTE_2
    ATTR_TABLE = SET_TO severity_level = NOTE
    -> ErrorsWithGeometry (output)
AttributeCreator_FAIL_2
    ATTR_TABLE = SET_TO severity_level = FAIL
    -> ErrorsWithGeometry (output)
AttributeCreator_FIXED_2
    ATTR_TABLE = SET_TO severity_level = FIXED
    -> ErrorsWithGeometry (output)
ErrorsWithGeometry (output)

FME custom transformer ValidateAttributes
This transformer validated all quality problems related to attribute information of the CityGML Building dataset. 
Input: CityGML dataset containing Buildings with all necessary attribute fields defined in OGC CityGML Encoding standard or Sig3D Modelling Guide for 3D Objects.
Output: Table containing all attribute problems

Parameters:
- CITYGML_ADDRESS =
- CITYGML_CLASS =
- CITYGML_FEATURE_ROLE =
- CITYGML_MEASURED_HEIGHT =
- CITYGML_MEASURED_HEIGHT_UNITS =
- CITYGML_RELATIVE_TO_TERRAIN =
- CITYGML_RELATIVE_TO_WATER =
- CITYGML_ROOF_TYPE =
- CITYGML_STOREYS_ABOVE_GROUND =
- CITYGML_STOREYS_BELOW_GROUND =
- CITYGML_STOREY_HEIGHTS_ABOVE_GROUND =
- CITYGML_STOREY_HEIGHTS_ABOVE_GROUND_UNITS =
- CITYGML_STOREY_HEIGHTS_BELOW_GROUND =
- CITYGML_STOREY_HEIGHTS_BELOW_GROUND_UNITS =
- CITYGML_TERMINATIONDATE =
- CITYGML_YEAR_OF_CONSTRUCTION =
- CITYGML_YEAR_OF_DEMOLITION =
- FME_BASENAME =
- FME_DATASET =
- FME_FEATURE_TYPE =
- FME_TYPE =
- GML_ID =
- GML_NAME =
- GML_PARENT_ID =

Input (input)
    -> CoordinateSystemRemover
CoordinateSystemRemover
    -> GeometryRemover
GeometryRemover
    -> FilterFeatureTypes
FilterFeatureTypes: AttributeFilter
    ATTR_NAME = fme_feature_type
    ATTR_VALUES = <Empty>,<Missing>,<Null>,<Unfiltered>,Building,BuildingPart
    Building -> AttributeValidator
    BuildingPart -> AttributeValidator
Note: This transformer checks attributes. / The default criteria are based on SIG3D Modelling Guide for 3d Objects Part 2 and OGC CityGML Specification. It is also possible to check attributes for other feature types (eg. RoofSurface) than Buildings. / Note: FME might warning about incomplete transformer, but that is ok.
AttributeValidator
    TABLE = citygml_roof_type,citygml_class,citygml_storeys_above_ground,citygml_storeys_below_ground,citygml_usage{0},citygml_function{0},citygml_measured_height,citygml_year_of_construction,gml_name;ATTRIBUTE_HAS_A_VALUE;<Unused>/citygml_class,citygml_usage{0},citygml_function{0},gml_name;TYPE;STRING/citygml_roof_type,citygml_storeys_above_ground,citygml_storeys_below_ground,citygml_measured_height,citygml_year_of_construction;TYPE;NUM/citygml_roof_type;RANGE;[1000,1130]/citygml_year_of_construction;RANGE;[0,2100]/citygml_usage{0},citygml_function{0};RANGE;[0,2700]/citygml_storeys_above_ground,citygml_storeys_below_ground,citygml_measured_height;RANGE;[0,]/citygml_class;RANGE;[1000,1180]
    FAILED -> AttributeKeeper_2
Note: Remove attributes after validation
AttributeKeeper_2
    CREATE_BULK_MODE_FEATURES = NO
    KEEP_ATTRS = gml_id,fme_dataset,fme_feature_type
    KEEP_LIST = _fme_validation_message_list{}
    -> ListExploder
Note: Find all errors
ListExploder
    ATTR_ACCUM_MODE = Merge List Attributes
    ATTR_CONFLICT_RES = Use List Attribute Values
    LIST_ATTR = _fme_validation_message_list{}
    ELEMENTS -> StringSearcher
Note: Find all invalid attributes
StringSearcher
    CASE = no
    MATCHED_RESULT_ATTR = _first_match
    REGEXP = '(.*?)'
    STRING_TO_SEARCH = @Value(_fme_validation_message_list)
    MATCHED -> TestFilter
Note: Filter errors based on its type
TestFilter
    DEFAULT_VALUE = <UNFILTERED>
    TEST_LIST = "BOOL_OP,OR,COMPOSITE_TEST,""""""1"""""",TEST_CLAUSE,CASE_INSENSITIVE_TEST @Value(_fme_validation_message_list) CONTAINS Has a value",@Value(_fme_validation_message_list) CONTAINS Has a value,"BOOL_OP,OR,COMPOSITE_TEST,""""""1"""""",TEST_CLAUSE,CASE_INSENSITIVE_TEST @Value(_fme_validation_message_list) CONTAINS Type is",@Value(_fme_validation_message_list) CONTAINS Type is,"BOOL_OP,OR,COMPOSITE_TEST,""""""1"""""",TEST_CLAUSE,CASE_INSENSITIVE_TEST @Value(_fme_validation_message_list) CONTAINS In range",@Value(_fme_validation_message_list) CONTAINS In range
    @Value(_fme_validation_message_list) CONTAINS Has a value -> Aggregator
    @Value(_fme_validation_message_list) CONTAINS Type is -> Aggregator_3
    @Value(_fme_validation_message_list) CONTAINS In range -> Aggregator_2
Note: Aggregate similar errors based on gml_id
Aggregator
    ACCUM_ATTRS_NAME = Drop Incoming Attributes
    COUNT_ATTR = count
    GROUP_BY = gml_id fme_dataset fme_feature_type _first_match
    MODE = Attributes Only
    SEP = " "
    AGGREGATE -> AttributeCreator
Note: Format an errors
AttributeCreator
    ATTR_TABLE:
      SET_TO error_name = MissingAttributeValue
      SET_TO details = Following attributes are missing: @Value(_first_match)
      SET_TO severity_level = NOTE
    -> AttributeRemover
Aggregator_3
    ACCUM_ATTRS_NAME = Drop Incoming Attributes
    COUNT_ATTR = count
    GROUP_BY = gml_id fme_dataset fme_feature_type _first_match
    MODE = Attributes Only
    SEP = " "
    AGGREGATE -> AttributeCreator_14
AttributeCreator_14
    ATTR_TABLE:
      SET_TO error_name = WrongDataType
      SET_TO details = The following attributes has wrong data type: @Value(_first_match)
      SET_TO severity_level = NOTE
    -> AttributeRemover
Aggregator_2
    ACCUM_ATTRS_NAME = Drop Incoming Attributes
    COUNT_ATTR = count
    GROUP_BY = gml_id fme_dataset fme_feature_type _first_match
    MODE = Attributes Only
    SEP = " "
    AGGREGATE -> AttributeCreator_2
AttributeCreator_2
    ATTR_TABLE:
      SET_TO error_name = ValueNotInAllowedRange
      SET_TO details = The following values are not in allowed range: @Value(_first_match)
      SET_TO severity_level = NOTE
    -> AttributeRemover
AttributeRemover
    REMOVE_ATTRS = _first_match
    -> Errors (output)
Errors (output)

FME custom transformer ValidateAddress
This transformer validates all quality problems related to Address features of the CityGML Building dataset.
Input: CityGML dataset containing Buildings 
Output: Table containing all address problems of the features

Parameters:
- CITYGML_ADDRESS =
- FME_DATASET =
- FME_FEATURE_TYPE =
- GML_ID =
- GML_PARENT_ID =

Input (input)
    -> Tester_2
Tester_2
    BOOL_OP = OR
    COMPOSITE_TEST = 1
    TEST_CLAUSE = TEST @Value(fme_feature_type) = Address
    TEST_MODE = TEST
    PASSED -> GeometryRemover
GeometryRemover
    -> XMLFlattener
Note: Expose XML address features to attributes
XMLFlattener
    ATTRIBUTE_XML = citygml_address
    EMBEDDED_EXPRESSIONS = "Country" "Locality" "PostalCode" "Thoroughfare"
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes=""/>
    NEW_ATTRIBUTES = CountryName LocalityName PostalCodeNumber ThoroughfareName ThoroughfareNumber
    XML_SOURCE_TYPE = Attribute with XML document
    -> AttributeValidator
    <REJECTED> -> AttributeValidator
Note: Check that address feature contain all needed parts. Also other checks can be done (eg. check that postal code is numerical).
AttributeValidator
    TABLE = CountryName,LocalityName,PostalCodeNumber,ThoroughfareName,ThoroughfareNumber;ATTRIBUTE_HAS_A_VALUE;<Unused>
    FAILED -> ListConcatenator_3
Errors (output)

Bookmark: Format errors
ListConcatenator_3
    DROP_EMPTY_PARTS = No
    LIST_ATTR = _fme_validation_message_list{}
    SEP = ;
    VAL_ATTR = _concatenated
    -> StringReplacer_3
StringReplacer_3
    CASE = NO
    FIND_TEXT = (Attribute ')|(' fails check for Has a Value)
    NO_MATCH = _FME_NO_OP_
    REGEXP = YES
    SRC_ATTRS = _concatenated
    -> AttributeCreator_3
AttributeCreator_3
    ATTR_TABLE:
      SET_TO error_name = MissingAddressInformation
      SET_TO details = The following address information does not exist: @Value(_concatenated)
      SET_TO severity_level = NOTE
    -> AttributeKeeper
AttributeKeeper
    CREATE_BULK_MODE_FEATURES = NO
    KEEP_ATTRS = details,error_name,fme_dataset,gml_id,severity_level
    -> Errors (output)

FME custom transformer ValidateXlinks
This transformers applies rules for xlinks. It checks that every surface is linked to solid with valid xlink.

Parameters:
- CITYGML_FEATURE_ROLE =
- FME_DATASET =
- FME_FEATURE_TYPE =
- GML_ID =
- GML_PARENT_ID =

Input (input)
    -> CoordinateSystemRemover
Note: Xlinks checks - xlink surfaces are extracted from solids and their gml:id's are compared to bounding surfaces to see if there is a match. This can be fairly intensive (and complicated).
CoordinateSystemRemover
    -> FeatureTypeFilter
FeatureTypeFilter
    ATTRIBUTES = <Blank>,<Unfiltered>,Building,BuildingPart
    <UNFILTERED> -> Tester_4
    Building -> GeometryPartExtractor
    BuildingPart -> GeometryPartExtractor
Note: Select only features where feature role = BoundedBy
Tester_4
    BOOL_OP = OR
    COMPOSITE_TEST = 1
    TEST_CLAUSE = TEST @Value(citygml_feature_role) = boundedBy
    TEST_MODE = TEST
    PASSED -> GeometryPartExtractor_2
Note: Extract surfaces for xlink checks
GeometryPartExtractor_2
    GQUERY:
      for $geom in //geometry
      where ($geom/@fme_geometry_type = 'IFMEFace'
      or $geom/@fme_geometry_type = 'IFMECompositeSurface')
      and fme:get-trait-property($geom, 'gml_id', $fme:HASAVALUE)
      return number($geom/@fme_id)
    EXTRACTED -> GeometryPropertyRenamer
    UNTOUCHED -> GeometryPropertyRenamer
Note: Rename original glm_id to compare features
GeometryPropertyRenamer
    PARAM_LIST = gml_id,trait_gml_id
    RENAMETYPE_PARAM = Traits
    RENAMED -> GeometryPropertyExtractor
    UNTOUCHED -> GeometryPropertyExtractor
Note: Create new gml_id
GeometryPropertyExtractor
    EXTRACTTYPE_PARAM = Traits
    PREFIX_EXTRACTED_TRAITS = No
    TRAIT_ATTR_LIST = trait_gml_id,No
    EXTRACTED -> GeometryRemover_3
GeometryRemover_3
    -> FeatureJoiner [LEFT]
Note: Extract xlinked surfaces from lod2Solids
GeometryPartExtractor
    GQUERY:
      for $geom in //geometry
      where $geom/ancestor::geometry/@fme_geometry_type = 'IFMEBRepSolid'
      and $geom/ancestor::geometry/@fme_geometry_name = 'lod2Solid'
      and fme:get-trait-property($geom, 'xlink_href', $fme:HASAVALUE)
      return number($geom/@fme_id)
    EXTRACTED -> GeometryPropertyExtractor_2
    UNTOUCHED -> GeometryRemover
Note: Extract xlink:href to attribute
GeometryPropertyExtractor_2
    EXTRACTTYPE_PARAM = Traits
    GQUERY:
      for $geom in //geometry
      where fme:get-trait-property($geom, 'xlink_href', $fme:HASAVALUE)
      and $geom/@fme_geometry_type = 'IFMEFace'
      return number($geom/@fme_id)
    PREFIX_EXTRACTED_TRAITS = No
    TRAIT_ATTR_LIST = xlink_href,No
    EXTRACTED -> AttributeTrimmer
Note: Remove #
AttributeTrimmer
    SRC_ATTRS = xlink_href
    TRIM_CHARS = "# "
    TRIM_TO_NONE = Yes
    TRIM_TYPE = Both
    -> GeometryRemover_2
GeometryRemover_2
    -> FeatureJoiner [RIGHT]
Note: Test connections between gml_id and xlink_href
FeatureJoiner
    ATTR_CONFLICT_RES = Use Left
    GEOMETRY_HANDLING = Use Left
    JOIN_KEYS = trait_gml_id xlink_href STRING
    JOIN_MODE = Inner
    UNJOINED_RIGHT -> AttributeCreator_2
Note: If xlink:href does not match with any gml_id, add an error
AttributeCreator_2
    ATTR_TABLE:
      SET_TO error_name = MissingXLink
      SET_TO details = Xlink:href of the building do not match with any gml_id of the features
      SET_TO severity_level = NOTE
      SET_TO count = 1
    -> Errors (output)
GeometryRemover
    -> AttributeCreator_16
Note: If the solid does not contain any linked surfaces, add an error
AttributeCreator_16
    ATTR_TABLE:
      SET_TO error_name = LOD2SolidMissingXlinks
      SET_TO details = Lod2Solid does not contain Xlinks.
      SET_TO severity_level = NOTE
      SET_TO count = 1
    -> Errors (output)
Errors (output)

FME custom transformer ValidateHierarchy
This transformer checks that every LoD2 level Building/BuildingPart has at least one roof, wall, groundsurface and address. Also check that every citymodel has at least one building.

Parameters:
- CITYGML_FEATURE_ROLE =
- FME_DATASET =
- FME_FEATURE_TYPE =
- GML_ID =
- GML_PARENT_ID =

Note: Hierarchy checks: this embedded transformer compares gml_parent_id to gml_id. The value of the “gml_parent_id” of a child element should be equal to the value of the “gml_id” of its parent element.. If there are no counterpart for every gml_parent_id (ie. feature has no parent), the error is pointed out. Only citymodels does not need to have parent id as it is top-level feature collection. / Note: InlineQuerier and SQL might be an alternative way to do this.
Input (input)
    -> GeometryRemover
GeometryRemover
    -> CoordinateSystemRemover
CoordinateSystemRemover
    -> FeatureTypeFilter_4
FeatureTypeFilter_4
    ATTRIBUTES = <Blank>,<Unfiltered>,GroundSurface,RoofSurface,CeilingSurface,OuterCeilingSurface,FloorSurface,OuterFloorSurface,WallSurface,InteriorWallSurface,Building,BuildingPart,Address,CityModel
    GroundSurface -> GroundToBuilding [RIGHT]
    RoofSurface -> RoofToBuilding [RIGHT]
    WallSurface -> WallToBuilding [RIGHT]
    Building -> Junction
    BuildingPart -> Junction
    Address -> AddressToBuilding [RIGHT]
    CityModel -> BuildingToCityModel [LEFT]
Junction
    -> GroundToBuilding [LEFT]
    -> WallToBuilding [LEFT]
    -> RoofToBuilding [LEFT]
    -> BuildingToCityModel [RIGHT]
    -> AddressToBuilding [LEFT]
Note: Add severity_level and count
AttributeCreator_7
    ATTR_TABLE:
      SET_TO severity_level = NOTE
      SET_TO count = 1
    -> Errors (output)
Errors (output)

Bookmark: Join features based on gml_id and gml_parent_id to see, if something is missing
GroundToBuilding: FeatureJoiner
    ATTR_CONFLICT_RES = Use Left
    GEOMETRY_HANDLING = Use Left
    JOIN_KEYS = gml_id gml_parent_id AUTO
    JOIN_MODE = Inner
    UNJOINED_LEFT -> AttributeCreator_3
    UNJOINED_RIGHT -> AttributeCreator_10
WallToBuilding: FeatureJoiner
    ATTR_CONFLICT_RES = Use Left
    GEOMETRY_HANDLING = Use Left
    JOIN_KEYS = gml_id gml_parent_id AUTO
    JOIN_MODE = Inner
    UNJOINED_LEFT -> AttributeCreator
    UNJOINED_RIGHT -> AttributeCreator_9
RoofToBuilding: FeatureJoiner
    ATTR_CONFLICT_RES = Use Left
    GEOMETRY_HANDLING = Use Left
    JOIN_KEYS = gml_id gml_parent_id AUTO
    JOIN_MODE = Inner
    UNJOINED_LEFT -> AttributeCreator_2
    UNJOINED_RIGHT -> AttributeCreator_8
BuildingToCityModel: FeatureJoiner
    ATTR_CONFLICT_RES = Use Left
    GEOMETRY_HANDLING = Use Left
    JOIN_KEYS = gml_id gml_parent_id AUTO
    JOIN_MODE = Inner
    UNJOINED_LEFT -> AttributeCreator_6
AddressToBuilding: FeatureJoiner
    ATTR_CONFLICT_RES = Use Left
    GEOMETRY_HANDLING = Use Left
    JOIN_KEYS = gml_id gml_parent_id AUTO
    JOIN_MODE = Inner
    UNJOINED_LEFT -> AttributeCreator_5
    UNJOINED_RIGHT -> AttributeCreator_4

Bookmark: If yes, add an error
AttributeCreator_3
    ATTR_TABLE:
      SET_TO error_name = BuildingWithoutGround
      SET_TO details = Buildings or BuildingParts has no GroundSurface.
    -> AttributeCreator_7
AttributeCreator_10
    ATTR_TABLE:
      SET_TO error_name = GroundWithoutBuilding
      SET_TO details = GroundSurface can not be assigned to any Building or BuildingPart.
    -> AttributeCreator_7
AttributeCreator
    ATTR_TABLE:
      SET_TO error_name = BuildingWithoutWall
      SET_TO details = Buildings or BuildingParts has no WallSurface.
    -> AttributeCreator_7
AttributeCreator_9
    ATTR_TABLE:
      SET_TO error_name = WallWithoutBuilding
      SET_TO details = WallSurface can not be assigned to any Building or BuildingPart.
    -> AttributeCreator_7
AttributeCreator_2
    ATTR_TABLE:
      SET_TO error_name = BuildingWithoutRoof
      SET_TO details = Buildings or BuildingParts has no RoofSurface.
    -> AttributeCreator_7
AttributeCreator_8
    ATTR_TABLE:
      SET_TO error_name = RoofWithoutBuilding
      SET_TO details = RoofSurface can not be assigned to any Building or BuildingPart.
    -> AttributeCreator_7
AttributeCreator_6
    ATTR_TABLE:
      SET_TO error_name = CityModelWithoutBuildings
      SET_TO details = CityModel has none Buildings or BuildingParts.
    -> AttributeCreator_7
AttributeCreator_5
    ATTR_TABLE:
      SET_TO error_name = BuildingWithoutAddress
      SET_TO details = Building or BuildingPart has no address feature.
    -> AttributeCreator_7
AttributeCreator_4
    ATTR_TABLE:
      SET_TO error_name = AddressWithoutBuilding
      SET_TO details = Address feature can not be assigned to any Building or BuildingPart.
    -> AttributeCreator_7

FME custom transformer CompareRoofToFloor
This transformers compares building heights in a following way:
1. It check that maximum height of the roof is higher than maximum height of the floor 
2. It check that minimum height or the roof is higher than minimum height or the floor
If not, the errors will be listed to output port.

Parameters:
- FME_DATASET =
- FME_FEATURE_TYPE =
- GML_ID =
- GML_PARENT_ID =

Input (input)
    -> FeatureTypeFilter
FeatureTypeFilter
    ATTRIBUTES = <Blank>,<Unfiltered>,GroundSurface,RoofSurface
    GroundSurface -> MaxMinGround
    RoofSurface -> MaxMinRoof
Note: Calculate maximum and minimum values for roof and grounds.
MaxMinGround: BoundsExtractor
    ZMAX = _GroundZMax
    ZMIN = _GroundZMin
    -> AggregateToMax_2
    -> AggregateToMin_2
Note: Select only highest and lowest values per building
AggregateToMax_2: StatisticsCalculator
    CALCULATION_MODE = NUMERIC
    FEAT_STATS = _GroundZMax,NUMERIC_MODE,,MAX,,,,,,,,,,,
    GROUP_BY = gml_parent_id fme_dataset fme_feature_type gml_id
    SUMMARY -> FeatureMerger [REQUESTOR]
AggregateToMin_2: StatisticsCalculator
    CALCULATION_MODE = NUMERIC
    FEAT_STATS = _GroundZMin,NUMERIC_MODE,MIN,,,,,,,,,,,,
    GROUP_BY = gml_parent_id fme_dataset fme_feature_type gml_id
    SUMMARY -> FeatureMerger_2 [REQUESTOR]
MaxMinRoof: BoundsExtractor
    ZMAX = _RoofZMax
    ZMIN = _RoofZMin
    -> AggregateToMax
    -> AggregateToMin
AggregateToMax: StatisticsCalculator
    CALCULATION_MODE = NUMERIC
    FEAT_STATS = _RoofZMax,NUMERIC_MODE,,MAX,,,,,,,,,,,
    GROUP_BY = gml_parent_id fme_dataset fme_feature_type gml_id
    SUMMARY -> FeatureMerger [SUPPLIER]
Note: Merge highest values of the roofs and highest values of the grounds.
FeatureMerger
    ATTR_ACCUM_MODE = Merge Supplier
    ATTR_CONFLICT_RES = Use Requestor
    IGNORE_NULLS = No
    JOIN_KEYS = @Value(gml_parent_id) @Value(gml_parent_id) AUTO
    MERGE_TYPE = Attributes Only
    PROCESS_DUPS = NO
    REJECT_NULL_MISSING_KEYS = No
    SUPPLIERS_FIRST = No
    MERGED -> MaxGroundVSMaxRoof
Note: Check that highest value of the roof is higher than highest value of the ground.
MaxGroundVSMaxRoof: Tester
    BOOL_OP = OR
    COMPOSITE_TEST = 1
    TEST_CLAUSE = TEST @Value(_RoofZMax.max) >= @Value(_GroundZMax.max)
    TEST_MODE = TEST
    FAILED -> AttributeCreator_2
Note: if not, add an error
AttributeCreator_2
    ATTR_TABLE:
      SET_TO error_name = MaxGroundHigherThanMaxRoof
      SET_TO details = The maximum height of the floor cannot be smaller than maximum height of the roof.
    -> GeometryRemover_2
    -> IssueLocations (output)
AggregateToMin: StatisticsCalculator
    CALCULATION_MODE = NUMERIC
    FEAT_STATS = _RoofZMin,NUMERIC_MODE,MIN,,,,,,,,,,,,
    GROUP_BY = gml_parent_id fme_dataset fme_feature_type gml_id
    SUMMARY -> FeatureMerger_2 [SUPPLIER]
FeatureMerger_2
    ATTR_ACCUM_MODE = Merge Supplier
    ATTR_CONFLICT_RES = Use Requestor
    IGNORE_NULLS = No
    JOIN_KEYS = @Value(gml_parent_id) @Value(gml_parent_id) AUTO
    MERGE_TYPE = Attributes Only
    PROCESS_DUPS = NO
    REJECT_NULL_MISSING_KEYS = No
    SUPPLIERS_FIRST = No
    MERGED -> MinGroundVSMinRoof
MinGroundVSMinRoof: Tester
    BOOL_OP = OR
    COMPOSITE_TEST = 1
    TEST_CLAUSE = TEST @Value(_GroundZMin.min) <= @Value(_RoofZMin.min)
    TEST_MODE = TEST
    FAILED -> AttributeCreator
AttributeCreator
    ATTR_TABLE:
      SET_TO error_name = MinGroundHigherThanMinRoof
      SET_TO details = The minimum height of the roof cannot be smaller than minimum height of the ground.
    -> GeometryRemover_2
    -> IssueLocations (output)
IssueLocations (output)
Note: Remove geometries and CRS to speed up processing
GeometryRemover_2
    -> CoordinateSystemRemover
CoordinateSystemRemover
    -> Errors (output)
Errors (output)

FME custom transformer CheckNormals
Normals check: this embedded transformer checks that every feature has logical orientation depending on its type. For roofs, grounds and walls, x-normals should differ according to following classifications:
Walls: Between -0.1 and 0.1 (almost vertical (0 is exactly vertical))
Roofs: More than 0.1 (not vertical, but face must be up)
Grounds: Exactly -1 (face down)

Parameters:
- CheckVertexNormals =
- FME_DATASET =
- FME_FEATURE_TYPE =
- FME_TYPE =
- GML_ID =
- GML_PARENT_ID =

Note: This embedded transformer checks that every feature has logical orientation depending on its type. For example, GroundSurfaces must be horizontal and WallSurfaces (almost) vertical.
Input (input)
    -> FeatureTypeFilter
Note: Select surfaces to be checked
FeatureTypeFilter
    ATTRIBUTES = <Blank>,<Unfiltered>,GroundSurface,RoofSurface,WallSurface
    GroundSurface -> Deaggregator_4
    RoofSurface -> Deaggregator_4
    WallSurface -> Deaggregator_4
Note: Flatten surfaces to single face
Deaggregator_4
    ATTR_ACCUM_MODE = Merge List Attributes
    ATTR_CONFLICT_RES = Use List Attribute Values
    EXPLODE_INSTANCES = No
    LIST_ATTR_MODE_LOOKUP = LEAN
    MODE = Flatten One Level
    SPLIT_COMPOSITES = Yes
    DEAGGREGATED -> GeometryValidator_2
Note: Create vertex normals on faces
GeometryValidator_2
    ISSUE_ATTR_NAME = _issues
    PRESETS = Custom
    REPAIR = Yes
    RULES = MISSING_VERTEX_NORMALS FME_CONTROLLER_QUERY_FILE]transformers/dependencies/geometryvalidator/MISSING_VERTEX_NORMALS.fme]FME_CONTROLLER_CHOICE]MISSING_VERTEX_NORMALS
    SUMMARY = Brief
    PASSED -> MeasureExtractor_2
    REPAIRED -> MeasureExtractor_2
    ISSUE_LOCATIONS -> Tester_2
Note: Extract only z normal of every face
MeasureExtractor_2
    GEOM_TYPE = Individual Vertex by Index
    INDEX = 0
    MEASURE_ATTR = _z_normal
    MEASURE_NAME = fme_vertex_normal_z
    -> TestFilter
Note: Test that every z-normal has correct orientation depending on the feature type. / Faces with negative value of z-normals points downwards and faces with positive values points upwards. When the face is exactly vertical, z-normal is 0.
TestFilter
    DEFAULT_VALUE = Invalid Surfaces
    TEST_LIST:
      "BOOL_OP,AND,COMPOSITE_TEST,""""""1 AND 2"""""",TEST_CLAUSE,TEST @Evaluate(@abs(@Value(_z_normal))) < 0.1
      TEST @Value(fme_feature_type) = WallSurface",WallSurface OK,"BOOL_OP,AND,COMPOSITE_TEST,""""""1 AND 2"""""",TEST_CLAUSE,TEST @Evaluate(@Value(_z_normal)) = -1
      TEST @Value(fme_feature_type) = GroundSurface",GroundSurface OK,"BOOL_OP,AND,COMPOSITE_TEST,""""""1 AND 2"""""",TEST_CLAUSE,TEST @Evaluate(@Value(_z_normal)) > 0
      TEST @Value(fme_feature_type) = RoofSurface",RoofSurface OK
    Invalid Surfaces -> GeometryRemover
    Invalid Surfaces -> AttributeCreator_3
GeometryRemover
    -> Aggregator_2
Note: If orientation is not correct, aggregate faces to single surface feature
Aggregator_2
    ACCUM_ATTRS_NAME = Use Attributes From One Feature
    AGGREGATE_TYPE = Homogeneous Collection (If Possible)
    COUNT_ATTR = count
    GROUP_BY = gml_id
    MODE = Geometry - Assemble One Level
    SEP = ,
    AGGREGATE -> AttributeCreator_2
Note: Add an error
AttributeCreator_2
    ATTR_TABLE:
      SET_TO error_name = FacesWronglyOriented
      SET_TO details = The faces of the feature are not correctly oriented based on vertex normals.
    -> Errors (output)
AttributeCreator_3
    ATTR_TABLE:
      SET_TO error_name = FacesWronglyOriented
      SET_TO details = The faces of the feature are not correctly oriented based on vertex normals.
    -> IssueLocations (output)
Note: See if missing vertex normals would raise an error based on user parameters
Tester_2
    BOOL_OP = OR
    COMPOSITE_TEST = 1
    TEST_CLAUSE = TEST $(CheckVertexNormals) = Yes
    TEST_MODE = TEST
    PASSED -> GeometryRemover_2
    PASSED -> AttributeCreator_5
GeometryRemover_2
    -> Aggregator_3
Note: If yes, aggregate faces to single surface feature
Aggregator_3
    ACCUM_ATTRS_NAME = Merge Incoming Attributes
    GROUP_BY = gml_id
    MODE = Attributes Only
    SEP = ,
    AGGREGATE -> AttributeCreator_4
Note: Add an error
AttributeCreator_4
    ATTR_TABLE:
      SET_TO error_name = @Value(issue_found)
      SET_TO details = The feature does not contain vertex normals.
    -> Errors (output)
Errors (output)
AttributeCreator_5
    ATTR_TABLE:
      SET_TO error_name = @Value(issue_found)
      SET_TO details = The feature does not contain vertex normals.
    -> IssueLocations (output)
IssueLocations (output)

FME custom transformer ValidateCRS
This transformer checks two rules:
1. Every building must have coordinate reference system
2. Coordinate systems must be 3D 
3. Features do not contain mixtures of 2D and 3D parts 
In addition, this transformer set CRS.

Parameters:
- COORD_PREC =
- CRS =
- FME_DATASET =
- FME_FEATURE_TYPE =
- FME_TYPE =
- GML_ID =
- GML_NAME =
- GML_PARENT_ID =
- Transformer_parameters =

Input (input)
    -> FeatureTypeFilter
FeatureTypeFilter
    ATTRIBUTES = <Blank>,<Unfiltered>,Address,CityModel
    <UNFILTERED> -> CoordinateSystemExtractor
    Address -> Passed (output)
    CityModel -> Passed (output)
CoordinateSystemExtractor
    CRDSYS_ATTR = _coordsys
    -> DimensionExtractor
DimensionExtractor
    DIM_ATTR = _dimension
    -> CheckCRS
Note: Check that every feature has coordinate reference system
CheckCRS: Tester
    BOOL_OP = OR
    COMPOSITE_TEST = 1
    TEST_CLAUSE = TEST _coordsys ATTRIBUTE_HAS_A_VALUE ""
    TEST_MODE = TEST
    PASSED -> Check3D
    FAILED -> AttributeCreator
    FAILED -> Check3D
Note: Check that coordinate reference systema are 3D
Check3D: Tester
    BOOL_OP = OR
    COMPOSITE_TEST = 1
    TEST_CLAUSE = TEST @Value(_dimension) = 3
    TEST_MODE = TEST
    PASSED -> GeometryValidator
    FAILED -> AttributeCreator_2
    FAILED -> GeometryValidator
Note: Check that features do not contain mixture of 2D and 3D parts.
GeometryValidator
    ISSUE_ATTR_NAME = _issues
    PRESETS = Custom
    REPAIR = No
    RULES = MISMATCHED_DIMENSIONS FORCE_DIMENSION]3D]MISMATCHED_Z_VAL]0]FME_CONTROLLER_QUERY_FILE]transformers/dependencies/geometryvalidator8/MISMATCHED_DIMENSIONS.fme]FME_CONTROLLER_CHOICE]MISMATCHED_DIMENSIONS
    SUMMARY = Brief
    PASSED -> Tester_8
    ISSUE_LOCATIONS -> AttributeCreator_3
    INVALID_PARTS -> ListExploder_2
Note: See, if user has defined destional coordinate reference system.
Tester_8
    BOOL_OP = OR
    COMPOSITE_TEST = 1
    TEST_CLAUSE = TEST $(CRS) != ""
    TEST_MODE = TEST
    PASSED -> CsmapReprojector
    FAILED -> Tester_2
Note: If yes, reproject the data
CsmapReprojector
    DEST = $(CRS)
    INTERPOLATION_TYPE_NAME = Nearest Neighbor
    RASTER_CELL_SIZE = Preserve Cells
    RASTER_TOLERANCE = 0.0
    VERTICAL_HANDLING = Ignore heights and leave them unchanged
    REPROJECTED -> Tester_2
Note: See, if COORD_PREC has a value
Tester_2
    BOOL_OP = OR
    COMPOSITE_TEST = 1
    TEST_CLAUSE = TEST $(COORD_PREC) != ""
    TEST_MODE = TEST
    PASSED -> CoordinateRounder
    FAILED -> Passed (output)
Note: If yes, round coordinates
CoordinateRounder
    XPREC = $(COORD_PREC)
    YPREC = $(COORD_PREC)
    ZPREC = $(COORD_PREC)
    ROUNDED -> Passed (output)
Passed (output)
Note: Expose the list of errors including error name
ListExploder_2
    ATTR_ACCUM_MODE = Merge List Attributes
    ATTR_CONFLICT_RES = Use List Attribute Values
    LIST_ATTR = _issues{}
    ELEMENTS -> ListExploder_4
Note: Expose details
ListExploder_4
    ATTR_ACCUM_MODE = Merge List Attributes
    ATTR_CONFLICT_RES = Use List Attribute Values
    LIST_ATTR = supplementary_info{}
    ELEMENTS -> AttributeManager_2
Note: Remove and format attributes
AttributeManager_2
    ATTR_TABLE:
      RENAME_SET_VALUE issue_found > error_name
      REMOVE location_sample.x
      REMOVE location_sample.y
      REMOVE location_sample.z
      RENAME_SET_DEFAULT supplementary_info > details = FME_CONDITIONAL:DEFAULT_VALUE'_FME_NO_OP_'BOOL_OP;OR;COMPOSITE_TEST;1;TEST details ATTRIBUTE_IS_MISSING _FME_BLANK_STRING_'Miscellanous'FME_NUM_CONDITIONS2___
      REMOVE _coordsys
      REMOVE _dimension
      SET_TO severity_level = FAIL
    USER_EXPOSED_ATTRIBUTES = fid,fme_geometry
    -> ErrorsWithGeometry (output)
ErrorsWithGeometry (output)
AttributeCreator_3
    ATTR_TABLE:
      SET_TO error_name = _issues
      SET_TO severity_level = FAIL
    -> GeometryRemover
AttributeCreator_2
    ATTR_TABLE:
      SET_TO error_name = Not3D
      SET_TO details = Coordinate reference system is not 3D
      SET_TO severity_level = NOTE
    -> GeometryRemover
AttributeCreator
    ATTR_TABLE:
      SET_TO error_name = MissingCRS
      SET_TO details = Coordinate reference system does not exist
      SET_TO severity_level = NOTE
    -> GeometryRemover
GeometryRemover
    -> CoordinateSystemRemover
CoordinateSystemRemover
    -> TabularErrors (output)
TabularErrors (output)

FME custom transformer CheckSpikes
This transformer checks if BoundarySurface has spikes that exceed given thresholds.

Parameters:
- FME_DATASET =
- FME_FEATURE_TYPE =
- FME_TYPE =
- GML_ID =
- GML_PARENT_ID =
- SPIKE_ANGLE =

Input (input)
    -> Tester
Note: See, if the SPIKE_ANGLE has a value. If not, skip the rule.
Tester
    BOOL_OP = OR
    COMPOSITE_TEST = 1
    TEST_CLAUSE = TEST $(SPIKE_ANGLE) != ""
    TEST_MODE = TEST
    PASSED -> Tester_2
Note: Select only BoundarySurfaces
Tester_2
    BOOL_OP = OR
    COMPOSITE_TEST = 1
    TEST_CLAUSE = TEST @Value(fme_type) != fme_solid
    TEST_MODE = TEST
    PASSED -> Deaggregator_2
Note: Flatten surface features
Deaggregator_2
    ATTR_ACCUM_MODE = Merge List Attributes
    ATTR_CONFLICT_RES = Use List Attribute Values
    EXPLODE_INSTANCES = No
    LIST_ATTR_MODE_LOOKUP = LEAN
    MODE = Flatten One Level
    SPLIT_COMPOSITES = Yes
    DEAGGREGATED -> GeometryCoercer
Note: Convert features into polygons because SpikeRemover can handle polygons only
GeometryCoercer
    GQUERY:
      for $geom in //geometry
      where $geom/count(parent::geometry) = 0
      return number($geom/@fme_id)
    KIND = fme_polygon
    COERCED -> Aggregator_2
    UNTOUCHED -> Aggregator_2
Note: Aggregate polygonal features into building levell, but now in the polygon format
Aggregator_2
    ACCUM_ATTRS_NAME = Use Attributes From One Feature
    AGGREGATE_TYPE = Homogeneous Collection (If Possible)
    GROUP_BY = fme_dataset gml_parent_id gml_id
    MODE = Geometry - Assemble One Level
    SEP = ,
    AGGREGATE -> SpikeRemover
Note: Detect spikes based on user parameters
SpikeRemover
    DIMENSIONS = 3D
    ITERATIVE = No
    SPIKEANGLE = $(SPIKE_ANGLE)
    REMOVED -> AttributeCreator_2
    REMOVED -> GeometryRemover
GeometryRemover
    -> CoordinateSystemRemover
CoordinateSystemRemover
    -> Aggregator
Note: Aggregate erros to under single fid
Aggregator
    ACCUM_ATTRS_NAME = Drop Incoming Attributes
    COUNT_ATTR = count
    GROUP_BY = fme_dataset fme_feature_type fme_type gml_id gml_parent_id
    MODE = Attributes Only
    SEP = ,
    AGGREGATE -> AttributeCreator_7
Note: Add an error
AttributeCreator_7
    ATTR_TABLE:
      SET_TO error_name = FeatureHasSpikes
      SET_TO details = Feature cannot contain spikes that exceeds given tolerance (max angle: $(SPIKE_ANGLE) degrees, max length:  units)
    -> Errors (output)
Errors (output)
Note: Add an error
AttributeCreator_2
    ATTR_TABLE:
      SET_TO error_name = FeatureHasSpikes
      SET_TO details = Feature cannot contain spikes that exceeds given tolerance (max angle: $(SPIKE_ANGLE) degrees, max length:  units)
    -> IssueLocations (output)
IssueLocations (output)

FME custom transformer CoordinateSystemMapUnitExtractor
Extracts the map units from the defined coordinate system of the entering features.
Outputs:
_units: This feature's defined map unit.
eg. 'latlong' for degrees, 'm' for meters, 'ft' or 'us-ft' for feet.

Input (input)
    -> CoordinateSystemExtractor
CoordinateSystemExtractor
    CRDSYS_ATTR = _coordsys
    -> CoordinateSystemDescriptionConverter
CoordinateSystemDescriptionConverter
    DIRECTION_LONG = Convert From FME Representation
    KIND_LONG = PROJ.4 String
    SRC = _coordsys
    VAL_ATTR = _proj4_str
    -> StringSearcher_2
StringSearcher_2
    CASE = no
    MATCHED_RESULT_ATTR = _units
    REGEXP = (?<=proj=).*?(?=\s)
    STRING_TO_SEARCH = @Value(_proj4_str)
    MATCHED -> Tester
Tester
    BOOL_OP = OR
    COMPOSITE_TEST = 1
    TEST_CLAUSE = TEST @Value(_units) = longlat
    TEST_MODE = TEST
    PASSED -> Output (output)
    FAILED -> StringSearcher
StringSearcher
    CASE = no
    MATCHED_RESULT_ATTR = _units
    REGEXP = (?<=units=).*?(?=\s)
    STRING_TO_SEARCH = @Value(_proj4_str)
    MATCHED -> Output (output)
Output (output)

FME custom transformer SurfaceNormalCalculator
This custom transformer calculates the coefficients of unit normal vector for each introduced polygon (attributes "normalX", "normalY", "normalZ"). The angle (attribute Slope) to the vertical is also derived from the direction of the surface normal vector. Values of 0 indicate perpendicular, 90 horizontal polygons. Furthermore, the 2D area is output in the attribute "signedArea2D" per polygon. Depending on the sign, a statement can be made about the orientation of the polygon. Negative values indicate polygons clockwise, positive counter-clockwise direction-oriented.
In order to obtain meaningful results, it is important to ensure that only planar polygons are initiated. All non-area features are routed unchanged through the rejected port.

INPUT (input)
    -> GeometryFilter
Note: use only closed polygons
GeometryFilter
    BREAK_AGG = No
    POINT -> Invalid (output)
    LINE -> Invalid (output)
    ARC -> Invalid (output)
    AREA -> CoordinateCounter
    ELLIPSE -> Invalid (output)
    TEXT -> Invalid (output)
    RASTER -> Invalid (output)
    SURFACE -> Invalid (output)
    SOLID -> Invalid (output)
    COLLECTION -> Invalid (output)
    NULL -> Invalid (output)
CoordinateCounter
    CNT_ATTR = _coordcount
    -> PythonCaller
PythonCaller
    NEW_ATTRIBUTES = normalX normalY normalZ Slope signedArea2D
    PYTHONSOURCE:
      import math
      import fmeobjects
      # Template Function interface:
      def calcNormal(feature):

          counter0 = 0
          coordCount = feature.numVertices() - 1

          normalX = 0
          normalY = 0
          normalZ = 0
          areaTri = 0
          area = 0
          angle = 0

          # loop through the coordinates and calculate surface normal of the triangle formed by the
          # the point, its predecessor and its successor.
          while counter0 < coordCount:

              # get test coordinate and the ones before and after
              before = (counter0 + (coordCount - 1)) % coordCount
              after = (counter0 + (coordCount + 1)) % coordCount
              coords0 = feature.getCoordinate(before)
              coords1 = feature.getCoordinate(counter0)
              coords2 = feature.getCoordinate(after)

              # calculate normal
              x1 = coords0[0]
              x2 = coords1[0]
              x3 = coords2[0]

              y1 = coords0[1]
              y2 = coords1[1]
              y3 = coords2[1]

              z1 = coords0[2]
              z2 = coords1[2]
              z3 = coords2[2]

              normalX = normalX + ((y2-y1) * (z3-z1) - (y3-y1) * (z2-z1))
              normalY = normalY + ((z2-z1) * (x3-x1) - (z3-z1) * (x2-x1))
              normalZ = normalZ + ((x2-x1) * (y3-y1) - (x3-x1) * (y2-y1))

              counter0 = counter0 + 1

              # polygon area (Gauss area formula)
              areaTri = ((y2+y3)*(x2-x3))/2
              area = area + areaTri


          # normalize vector
          length = math.sqrt(normalX**2 + normalY**2 + normalZ**2)

          if length != 0:
              normalX = normalX / length
              normalY = normalY / length
              normalZ = normalZ / length
          else:
              normalX = 0
              normalY = 0
              normalZ = 0

          # angle
          if normalZ != 0:
              angle = math.fabs(math.atan(math.sqrt(normalX**2+normalY**2)/normalZ)*(180/3.14))
          else:
              angle = 90


          # write normal to feature
          feature.setAttribute('normalX',normalX)
          feature.setAttribute('normalY',normalY)
          feature.setAttribute('normalZ',normalZ)
          feature.setAttribute('signedArea2D',area)
          feature.setAttribute('Slope',angle)
    PYTHONSYMBOL = calcNormal
    -> AttributeRemover_3
AttributeRemover_3
    REMOVE_ATTRS = _coordcount
    -> Ok (output)
Ok (output)
Invalid (output)
